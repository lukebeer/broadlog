--===============================================================
-- File Name : BW-CCReportingDBManagement.mib
-- Author    : BroadSoft Inc.
-- Copyright 2000-2010, BroadSoft, Inc. All rights reserved. 
-- Proprietary Property of BroadSoft, Inc. Gaithersburg, MD.
--===============================================================

BW-CCReportingDBManagement DEFINITIONS ::= BEGIN
    IMPORTS
      MODULE-COMPLIANCE, OBJECT-GROUP          
        FROM SNMPv2-CONF
      enterprises, MODULE-IDENTITY, OBJECT-TYPE, Gauge32, Counter32
        FROM SNMPv2-SMI;

  broadsoft MODULE-IDENTITY
    LAST-UPDATED  "201008230000Z"
    ORGANIZATION  "Broadsoft, Inc"
    CONTACT-INFO  "Broadsoft, Inc
220 Perry Parkway
Gaithersburg, MD  20877

301-977-9440"
    DESCRIPTION
      "This is the MIB for the CC Reporting DB Management application."
    REVISION    "201008230000Z"
      DESCRIPTION     "Creation."
    ::= { enterprises 6431 }

  broadworks OBJECT IDENTIFIER
    ::= { broadsoft 1 }

  ccReportingDBManagement OBJECT IDENTIFIER
    ::= { broadworks 24 }

  ccrdbDatabaseModule OBJECT IDENTIFIER
    ::= { ccReportingDBManagement 1 }

  ccrdbDatabaseStats OBJECT IDENTIFIER
    ::= { ccrdbDatabaseModule 1 }

  ccrdbOracle OBJECT IDENTIFIER
    ::= { ccrdbDatabaseStats 1 }

  bwCCReportingDBManagementMibConformance OBJECT IDENTIFIER
    ::= { ccReportingDBManagement 1000 }

-- ccrdbOracle ::  ...............................

   bwCCReportingDBManagementOpenedTransactions  OBJECT-TYPE
      SYNTAX         Gauge32
      MAX-ACCESS     read-only
      STATUS         current
      DESCRIPTION
            "This counter reflects the total number of opened transaction with the database."
      ::=  {  ccrdbOracle  1  }

   bwCCReportingDBManagementCommittedTransactions  OBJECT-TYPE
      SYNTAX         Counter32
      MAX-ACCESS     read-write
      STATUS         current
      DESCRIPTION
            "This counter reflects the total number of committed transactions to the database since the last restart."
      ::=  {  ccrdbOracle  2  }

   bwCCReportingDBManagementFailedTransactions  OBJECT-TYPE
      SYNTAX         Counter32
      MAX-ACCESS     read-write
      STATUS         current
      DESCRIPTION
            "This counter reflects the total number of failed transactions with the database."
      ::=  {  ccrdbOracle  3  }

   bwCCReportingDBManagementCriticalErrors  OBJECT-TYPE
      SYNTAX         Counter32
      MAX-ACCESS     read-write
      STATUS         current
      DESCRIPTION
            "This counter reflects the total number of critical errors encountered during processing with the database."
      ::=  {  ccrdbOracle  4  }

-- BroadWorks CC Reporting DB Management MIB Conformance Definition  ...........................................

bwCCReportingDbManagementMibGroups     OBJECT IDENTIFIER ::= { bwCCReportingDBManagementMibConformance 1 }
bwCCReportingDbManagementMibCompliancy OBJECT IDENTIFIER ::= { bwCCReportingDBManagementMibConformance 2 }

bwCCReportingDbManagementStatsGroup OBJECT-GROUP
    OBJECTS { bwCCReportingDBManagementOpenedTransactions,
              bwCCReportingDBManagementCommittedTransactions,
              bwCCReportingDBManagementFailedTransactions,
              bwCCReportingDBManagementCriticalErrors }
  STATUS  current
  DESCRIPTION
     "This group defines statistics for the CC Reporting DB Management."
  ::= { bwCCReportingDbManagementMibGroups 1 }

  bwScfBasicCompliance MODULE-COMPLIANCE
    STATUS      current
    DESCRIPTION 
        "BroadWorks CC Reporting DB Management MIB compliance"

    MODULE

        MANDATORY-GROUPS        { bwCCReportingDbManagementStatsGroup }

    ::= { bwCCReportingDbManagementMibCompliancy 1 }

END
