--===============================================================
-- File Name : BW-Subscriber.mib
-- Author    : BroadSoft Inc.
-- Copyright 2000-2010, BroadSoft, Inc. All rights reserved. 
-- Proprietary Property of BroadSoft, Inc. Gaithersburg, MD.
--===============================================================

BW-Subscriber DEFINITIONS ::= BEGIN
    IMPORTS
      DateAndTime, DisplayString
        FROM SNMPv2-TC
      MODULE-COMPLIANCE, OBJECT-GROUP          
        FROM SNMPv2-CONF
      enterprises, MODULE-IDENTITY, OBJECT-TYPE, Gauge32, Counter32, Integer32, Unsigned32
        FROM SNMPv2-SMI;

  broadsoft MODULE-IDENTITY
    LAST-UPDATED  "201007230000Z"
    ORGANIZATION  "Broadsoft, Inc"
    CONTACT-INFO  "Broadsoft, Inc
220 Perry Parkway
Gaithersburg, MD  20877

301-977-9440"
    DESCRIPTION
      "This is the MIB for the BroadWorks Subscriber Agent."
    REVISION    "201007230000Z"
      DESCRIPTION     "Creation of the BroadWorks Subscriber Agent."
    ::= { enterprises 6431 }

  broadworks OBJECT IDENTIFIER
    ::= { broadsoft 1 }

  subscriber OBJECT IDENTIFIER
    ::= { broadworks 21 }

  cache OBJECT IDENTIFIER
    ::= { subscriber 1 }

  access OBJECT IDENTIFIER
    ::= { subscriber 2 }

  sh OBJECT IDENTIFIER
    ::= { subscriber 3 }

  db OBJECT IDENTIFIER
    ::= { subscriber 4 }

  diameterModule OBJECT IDENTIFIER
    ::= { subscriber 5 }

  shInterfaceModule OBJECT IDENTIFIER
    ::= { subscriber 6 }

-- Stats and other modules.

  diameterStats OBJECT IDENTIFIER
    ::= { diameterModule 1 }

  shInterfaceStats OBJECT IDENTIFIER
    ::= { shInterfaceModule 1 }

  bwSubscriberMibConformance OBJECT IDENTIFIER
    ::= { subscriber 100 }

-- SUBSCRIBER :: CACHE ...............................

	bwSubscriberCacheHits	OBJECT-TYPE
		SYNTAX			Counter32
		MAX-ACCESS		read-write
		STATUS			current
		DESCRIPTION
				"The number of cache hits."
		::=  {  cache  1  }

	bwSubscriberCacheMiss	OBJECT-TYPE
		SYNTAX			Counter32
		MAX-ACCESS		read-write
		STATUS			current
		DESCRIPTION
				"The number of cache miss."
		::=  {  cache  2  }

	bwSubscriberCacheEntriesTotal	OBJECT-TYPE
		SYNTAX			Gauge32
		MAX-ACCESS		read-only
		STATUS			current
		DESCRIPTION
				"The number of cache entries."
		::=  {  cache  3  }

	bwSubscriberCacheEntriesInMemory	OBJECT-TYPE
		SYNTAX			Gauge32
		MAX-ACCESS		read-only
		STATUS			current
		DESCRIPTION
				"The number of cache entries commited to memory."
		::=  {  cache  4  }

	bwSubscriberCacheEntriesOnDisk	OBJECT-TYPE
		SYNTAX			Gauge32
		MAX-ACCESS		read-only
		STATUS			current
		DESCRIPTION
				"The number of cache entries commited to disk."
		::=  {  cache  5  }

	bwSubscriberCacheDiskUsage	OBJECT-TYPE
		SYNTAX			Gauge32
		MAX-ACCESS		read-only
		STATUS			current
		DESCRIPTION
				"The current disk cache size in Mbytes."
		::=  {  cache  6  }

	bwSubscriberAccessIOWorkersBusy	OBJECT-TYPE
		SYNTAX			Gauge32
		MAX-ACCESS		read-only
		STATUS			current
		DESCRIPTION
				"The number i/o worker threads currently processing a packet."
		::=  {  access  1  }

	bwSubscriberAccessIOQueueSize	OBJECT-TYPE
		SYNTAX			Gauge32
		MAX-ACCESS		read-only
		STATUS			current
		DESCRIPTION
				"The number of packets currently queued for processingin the i/o queue"
		::=  {  access  2  }

	bwSubscriberAccessReadWorkersBusy	OBJECT-TYPE
		SYNTAX			Gauge32
		MAX-ACCESS		read-only
		STATUS			current
		DESCRIPTION
				"The number read worker threads currently processing profile retrieval."
		::=  {  access  3  }

	bwSubscriberAccessReadQueueSize	OBJECT-TYPE
		SYNTAX			Gauge32
		MAX-ACCESS		read-only
		STATUS			current
		DESCRIPTION
				"The number of profile retrieval requests currently queued for processing."
		::=  {  access  4  }

	bwSubscriberAccessWriteWorkersBusy	OBJECT-TYPE
		SYNTAX			Gauge32
		MAX-ACCESS		read-only
		STATUS			current
		DESCRIPTION
				"The number of write worker threads currently processing a profile update request."
		::=  {  access  5  }

	bwSubscriberAccessWriteQueueSize	OBJECT-TYPE
		SYNTAX			Gauge32
		MAX-ACCESS		read-only
		STATUS			current
		DESCRIPTION
				"The number of requests currently queued for processing"
		::=  {  access  6  }

	bwSubscriberAccessRetrieve	OBJECT-TYPE
		SYNTAX			Gauge32
		MAX-ACCESS		read-only
		STATUS			current
		DESCRIPTION
				"The number of retrieve requests processed."
		::=  {  access  7  }

	bwSubscriberAccessModify	OBJECT-TYPE
		SYNTAX			Gauge32
		MAX-ACCESS		read-only
		STATUS			current
		DESCRIPTION
				"The number of modify request processe. This measures the number of profile modification requests received from applications."
		::=  {  access  8  }

	bwSubscriberAccessRegister	OBJECT-TYPE
		SYNTAX			Counter32
		MAX-ACCESS		read-write
		STATUS			current
		DESCRIPTION
				"The number of register requests processed."
		::=  {  access  9  }

	bwSubscriberAccessErrors	OBJECT-TYPE
		SYNTAX			Counter32
		MAX-ACCESS		read-write
		STATUS			current
		DESCRIPTION
				"The number of errors responses generated."
		::=  {  access  10  }

	bwSubscriberAccessRegistrations	OBJECT-TYPE
		SYNTAX			Gauge32
		MAX-ACCESS		read-only
		STATUS			current
		DESCRIPTION
				"The number of active registrations."
		::=  {  access  11  }

	bwSubscriberAccessNotifications	OBJECT-TYPE
		SYNTAX			Counter32
		MAX-ACCESS		read-write
		STATUS			current
		DESCRIPTION
				"The number of change notifications generated."
		::=  {  access  12  }

	bwSubscriberShOperationMinTime	OBJECT-TYPE
		SYNTAX			Gauge32
		MAX-ACCESS		read-only
		STATUS			current
		DESCRIPTION
				"This is the minimum time the Subscriber Agent waited for a Sh operation to complete.  An operation can involve multiple Sh exchanges with the HSS.  An operation is typically a full profile read or write."
		::=  {  sh  1  }

	bwSubscriberShOperationMaxTime	OBJECT-TYPE
		SYNTAX			Gauge32
		MAX-ACCESS		read-only
		STATUS			current
		DESCRIPTION
				"This is the maximum time the Subscriber Agent waited for a Sh operation to complete.  An operation can involve multiple Sh exchanges with the HSS.  An operation is typically a full profile read or write."
		::=  {  sh  2  }

	bwSubscriberShOperationAverageTime	OBJECT-TYPE
		SYNTAX			Gauge32
		MAX-ACCESS		read-only
		STATUS			current
		DESCRIPTION
				"This is the average time the Subscriber Agent waited for Sh operation to complete.  An operation can involve multiple Sh exchanges with the HSS.  An operation is typically a full profile read or write."
		::=  {  sh  3  }

	bwSubscriberShOperations	OBJECT-TYPE
		SYNTAX			Counter32
		MAX-ACCESS		read-write
		STATUS			current
		DESCRIPTION
				"This is the number of completed Sh operations"
		::=  {  sh  4  }

	bwSubscriberDbQueryMinTime	OBJECT-TYPE
		SYNTAX			Gauge32
		MAX-ACCESS		read-only
		STATUS			current
		DESCRIPTION
				"This is the minimum time the Subscriber Agent waited for a database query to complete."
		::=  {  db  1  }

	bwSubscriberDbQueryMaxTime	OBJECT-TYPE
		SYNTAX			Gauge32
		MAX-ACCESS		read-only
		STATUS			current
		DESCRIPTION
				"This is the maximum time the Subscriber Agent waited for a database query to complete."
		::=  {  db  2  }

	bwSubscriberDbQueryAverageTime	OBJECT-TYPE
		SYNTAX			Gauge32
		MAX-ACCESS		read-only
		STATUS			current
		DESCRIPTION
				"This is the average time the Subscriber Agent waited for database queries to complete."
		::=  {  db  3  }

	bwSubscriberDbQueries	OBJECT-TYPE
		SYNTAX			Counter32
		MAX-ACCESS		read-write
		STATUS			current
		DESCRIPTION
				"This is the number of completed database queries."
		::=  {  db  4  }

-- DIAMETERSTATS ::  ...............................

  bwSubscriberDiameterTransactionTable OBJECT-TYPE
    SYNTAX      SEQUENCE OF BwSubscriberDiameterTransactionEntry
    MAX-ACCESS  not-accessible
    STATUS      current
    DESCRIPTION 
        "This table contains statistics about the Diameter Stack transactions."
    ::= { diameterStats 1 }

  bwSubscriberDiameterTransactionEntry OBJECT-TYPE
    SYNTAX      BwSubscriberDiameterTransactionEntry
    MAX-ACCESS  not-accessible
    STATUS      current
    DESCRIPTION 
        "This row contains the statistics for a given Diameter transaction."
    INDEX       { bwSubscriberDiameterCommandCode }
    ::= { bwSubscriberDiameterTransactionTable 1 }

  BwSubscriberDiameterTransactionEntry ::= SEQUENCE {
    bwSubscriberDiameterCommandCode                  Unsigned32,
    bwSubscriberDiameterRequestsOut                  Counter32,
    bwSubscriberDiameterInformationalAnswersIn       Counter32,
    bwSubscriberDiameterSuccessAnswersIn             Counter32,
    bwSubscriberDiameterFailureAnswersIn             Counter32,
    bwSubscriberDiameterRequestTimeouts              Counter32,
    bwSubscriberDiameterRequestsIn                   Counter32,
    bwSubscriberDiameterInformationalAnswersOut      Counter32,
    bwSubscriberDiameterSuccessAnswersOut            Counter32,
    bwSubscriberDiameterFailureAnswersOut            Counter32
  }

  bwSubscriberDiameterCommandCode OBJECT-TYPE
    SYNTAX      Unsigned32 
    MAX-ACCESS  read-only
    STATUS      current
    DESCRIPTION 
        "This is the Diameter message's command-code which indexes this table."
    ::= { bwSubscriberDiameterTransactionEntry 1 }

  bwSubscriberDiameterRequestsOut OBJECT-TYPE
    SYNTAX      Counter32
    MAX-ACCESS  read-write
    STATUS      current
    DESCRIPTION 
        "This is the number of requests sent by the Diameter stack, indexed by the message's Command-Code.  This includes both initial transmissions and retransmissions of the same request."
    ::= { bwSubscriberDiameterTransactionEntry 2 }

  bwSubscriberDiameterInformationalAnswersIn OBJECT-TYPE
    SYNTAX      Counter32
    MAX-ACCESS  read-write
    STATUS      current
    DESCRIPTION 
        "This is the number of answers containing an informational Result-Code (value 1xxx), indexed by the message's Command-Code."
    ::= { bwSubscriberDiameterTransactionEntry 3 }

  bwSubscriberDiameterSuccessAnswersIn OBJECT-TYPE
    SYNTAX      Counter32
    MAX-ACCESS  read-write
    STATUS      current
    DESCRIPTION 
        "This is the number of answers containing a successful Result-Code (value 2xxx), indexed by the message's Command-Code."
    ::= { bwSubscriberDiameterTransactionEntry 4 }

  bwSubscriberDiameterFailureAnswersIn OBJECT-TYPE
    SYNTAX      Counter32
    MAX-ACCESS  read-write
    STATUS      current
    DESCRIPTION 
        "This is the number of answers containing a failure Result-Code or Experimental-Result (value >= 3000), malformed answers, or answers that do not match any outstanding request.  Malformed answers have inappropriate Diameter message header values or do not contain any Result-Code or Experimental-Result AVPs."
    ::= { bwSubscriberDiameterTransactionEntry 5 }

  bwSubscriberDiameterRequestTimeouts OBJECT-TYPE
    SYNTAX      Counter32
    MAX-ACCESS  read-write
    STATUS      current
    DESCRIPTION 
        "This is the number of requests for which no response has been received within the specified timeout.  The timeout value is application-dependent.  If an answer is received afterward, it is treated as an unmatched answer and the bwDiameterFailureAnswersIn is incremented.  This value is indexed by the message's Command-Code."
    ::= { bwSubscriberDiameterTransactionEntry 6 }

  bwSubscriberDiameterRequestsIn OBJECT-TYPE
    SYNTAX      Counter32
    MAX-ACCESS  read-write
    STATUS      current
    DESCRIPTION 
        "This is the number of received requests on the corresponding Diameter stack instance, indexed by the message's Command-Code."
    ::= { bwSubscriberDiameterTransactionEntry 7 }

  bwSubscriberDiameterInformationalAnswersOut OBJECT-TYPE
    SYNTAX      Counter32
    MAX-ACCESS  read-write
    STATUS      current
    DESCRIPTION 
        "This is the number of informational answers (Result-Code value = 1xxx) sent by the corresponding Diameter stack instance, indexed by the message's Command-Code."
    ::= { bwSubscriberDiameterTransactionEntry 8 }

  bwSubscriberDiameterSuccessAnswersOut OBJECT-TYPE
    SYNTAX      Counter32
    MAX-ACCESS  read-write
    STATUS      current
    DESCRIPTION 
        "This is the number of successful answers (Result-Code value = 2xxx) sent by the corresponding Diameter stack instance, indexed by the message's Command-Code."
    ::= { bwSubscriberDiameterTransactionEntry 9 }

  bwSubscriberDiameterFailureAnswersOut OBJECT-TYPE
    SYNTAX      Counter32
    MAX-ACCESS  read-write
    STATUS      current
    DESCRIPTION 
        "This is the number of failure answers (Result-Code/Experimental-Result-Code value >= 3000) sent by the corresponding Diameter stack instance, indexed by the message's Command-Code."
    ::= { bwSubscriberDiameterTransactionEntry 10 }

-- Sh Interface Stats ::  ...............................

  bwShInterfaceServerUnreachable OBJECT-TYPE
    SYNTAX      Counter32
    MAX-ACCESS  read-write
    STATUS      current
    DESCRIPTION 
        "This is the number of Sh requests not sent because none of the HSSs, Diameter agents, or the Sh Execution Server relay (if operating in relay mode) is currently connected."
    ::= { shInterfaceStats 1 }

--
-- BroadWorks Common managed object MIB Conformance Definition  ...........................................
--

  bwSubscriberMibGroups OBJECT IDENTIFIER ::= { bwSubscriberMibConformance 1 }
  bwSubscriberMibCompliancy OBJECT IDENTIFIER ::= { bwSubscriberMibConformance 2 }

  bwSubscriberCacheStatsGroup OBJECT-GROUP
    OBJECTS { bwSubscriberCacheHits, bwSubscriberCacheMiss,
              bwSubscriberCacheEntriesTotal, bwSubscriberCacheEntriesInMemory,
              bwSubscriberCacheEntriesOnDisk, bwSubscriberCacheDiskUsage }
  STATUS  current
  DESCRIPTION
     "This group defines statistics for the Subscriber cache."
  ::= { bwSubscriberMibGroups 1 }

  bwSubscriberAccessStatsGroup OBJECT-GROUP
    OBJECTS { bwSubscriberAccessIOWorkersBusy, bwSubscriberAccessIOQueueSize, bwSubscriberAccessReadWorkersBusy,
              bwSubscriberAccessReadQueueSize, bwSubscriberAccessWriteWorkersBusy,
              bwSubscriberAccessWriteQueueSize, bwSubscriberAccessRetrieve,
              bwSubscriberAccessModify, bwSubscriberAccessRegister, 
              bwSubscriberAccessErrors, bwSubscriberAccessRegistrations,
              bwSubscriberAccessNotifications  }
  STATUS  current
  DESCRIPTION
     "This group defines statistics for the Subscriber Access."
  ::= { bwSubscriberMibGroups 2 }

  bwSubscriberShStatsGroup OBJECT-GROUP
    OBJECTS { bwSubscriberShOperationMinTime, bwSubscriberShOperationMaxTime,
              bwSubscriberShOperationAverageTime, bwSubscriberShOperations }
  STATUS  current
  DESCRIPTION
     "This group defines statistics for the Subscriber Sh."
  ::= { bwSubscriberMibGroups 3 }

  bwSubscriberDbStatsGroup OBJECT-GROUP
    OBJECTS { bwSubscriberDbQueryMinTime, bwSubscriberDbQueryMaxTime,
              bwSubscriberDbQueryAverageTime, bwSubscriberDbQueries }
  STATUS  current
  DESCRIPTION
     "This group defines statistics for the Subscriber Sh."
  ::= { bwSubscriberMibGroups 4 }

  bwSubscriberDiameterGroup OBJECT-GROUP
    OBJECTS { bwSubscriberDiameterCommandCode, bwSubscriberDiameterRequestsOut,
              bwSubscriberDiameterInformationalAnswersIn, bwSubscriberDiameterSuccessAnswersIn,
              bwSubscriberDiameterFailureAnswersIn, bwSubscriberDiameterRequestTimeouts,
              bwSubscriberDiameterRequestsIn, bwSubscriberDiameterInformationalAnswersOut,
              bwSubscriberDiameterSuccessAnswersOut, bwSubscriberDiameterFailureAnswersOut }
    STATUS current
    DESCRIPTION 
        "This group defines the Subscriber Diameter statistics."
    ::= { bwSubscriberMibGroups 5 }

  bwSubscriberShInterfaceStatsGroup OBJECT-GROUP
    OBJECTS { bwShInterfaceServerUnreachable }
    STATUS current
    DESCRIPTION 
        "This group defines the Subscriber Diameter Sh interface statistics."
    ::= { bwSubscriberMibGroups 6 }

  bwSubscriberBasicCompliance MODULE-COMPLIANCE
    STATUS      current
    DESCRIPTION 
        "BroadWorks Subscriber MIB compliance"

    MODULE      -- this module

        MANDATORY-GROUPS        { bwSubscriberCacheStatsGroup, bwSubscriberAccessStatsGroup,
                                  bwSubscriberShStatsGroup, bwSubscriberDbStatsGroup,
                                  bwSubscriberDiameterGroup, bwSubscriberShInterfaceStatsGroup }

    ::= { bwSubscriberMibCompliancy 1 }

END
