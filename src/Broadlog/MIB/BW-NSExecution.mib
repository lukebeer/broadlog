-- File Name : BW-NSExecution.mib

BW-NSExecution DEFINITIONS ::= BEGIN

IMPORTS
    MODULE-COMPLIANCE, OBJECT-GROUP
        FROM SNMPv2-CONF
    Counter32, Gauge32, Integer32, MODULE-IDENTITY, NOTIFICATION-TYPE, 
    OBJECT-TYPE, Unsigned32, enterprises
        FROM SNMPv2-SMI
    DisplayString
        FROM SNMPv2-TC;

broadsoft MODULE-IDENTITY
    LAST-UPDATED "200912020000Z"
    ORGANIZATION 
        "Broadsoft, Inc"
    CONTACT-INFO 
        "Broadsoft, Inc
         220 Perry Parkway
         Gaithersburg, MD  20877
         301-977-9440"
    DESCRIPTION 
        "This is the module defining the NSExecution application performance counters."
    REVISION    "200912020000Z"
    DESCRIPTION 
        "Creation of the NS Execution MIB based on the defunct BW-BroadworksNetworkServer MIB."
    ::= { enterprises 6431 }


broadworks OBJECT IDENTIFIER
    ::= { broadsoft 1 }

nsExecutionServer OBJECT IDENTIFIER
    ::= { broadworks 5 }

system OBJECT IDENTIFIER
    ::= { nsExecutionServer 1 }

licensing OBJECT IDENTIFIER
    ::= { system 11 }

bwNbTimePeriodWithLicenseViolations OBJECT-TYPE
    SYNTAX      Counter32
    MAX-ACCESS  read-only
    STATUS      current
    DESCRIPTION 
        "Number of Time Periods in which a license violation occurred"
    ::= { licensing 1 }

bwNbTransactionInViolation OBJECT-TYPE
    SYNTAX      Counter32
    MAX-ACCESS  read-only
    STATUS      current
    DESCRIPTION 
        "Number of transactions that were in violation since the last BroadWorks restart"
    ::= { licensing 2 }

bwNbThresholdAlarmSent OBJECT-TYPE
    SYNTAX      Counter32
    MAX-ACCESS  read-only
    STATUS      current
    DESCRIPTION 
        "Number of times a threshold alarm was sent since the last BroadWorks restart"
    ::= { licensing 3 }

bwNbNonInviteTimePeriodWithLicenseViolations OBJECT-TYPE
    SYNTAX      Counter32
    MAX-ACCESS  read-only
    STATUS      current
    DESCRIPTION 
        "Number of time periods in which a non-invite transaction license violation occurred."
    ::= { licensing 4 }

bwNbNonInviteTransactionInViolation OBJECT-TYPE
    SYNTAX      Counter32
    MAX-ACCESS  read-only
    STATUS      current
    DESCRIPTION 
        "Number of non-invite transactions that were in violation since the last BroadWorks restart."
    ::= { licensing 5 }

bwNbNonInviteThresholdAlarmSent OBJECT-TYPE
    SYNTAX      Counter32
    MAX-ACCESS  read-only
    STATUS      current
    DESCRIPTION 
        "Number of times a threshold alarm for non-invite transaction was sent since the last BroadWorks restart."
    ::= { licensing 6 }

internalStats OBJECT IDENTIFIER
    ::= { system 12 }

bwNSSystemInternalQueueResets OBJECT-TYPE
    SYNTAX      Counter32
    MAX-ACCESS  read-write
    STATUS      current
    DESCRIPTION 
        "When set to a value other then 0, all the internal queue statistic stored under bwNSSystemInternalQueueTable are reset to 0."
    ::= { internalStats 1 }

bwNSSystemInternalQueueTable OBJECT-TYPE
    SYNTAX      SEQUENCE OF BwNSSystemInternalQueueEntry
    MAX-ACCESS  not-accessible
    STATUS      current
    DESCRIPTION 
        "This table contains statistics about the BroadWorks internal queues"
    ::= { internalStats 2 }

bwNSSystemInternalQueueEntry OBJECT-TYPE
    SYNTAX      BwNSSystemInternalQueueEntry
    MAX-ACCESS  not-accessible
    STATUS      current
    DESCRIPTION 
        "This row contains the statistics for a given internal queue in the system"
    INDEX       { bwNSSystemInternalQueueIndex }
    ::= { bwNSSystemInternalQueueTable 1 }

BwNSSystemInternalQueueEntry ::= SEQUENCE {
    bwNSSystemInternalQueueIndex                    Unsigned32,
    bwNSSystemInternalQueueName                     DisplayString,
    bwNSSystemInternalQueueSize                     Counter32,
    bwNSSystemInternalQueueTimeAvg                  Gauge32,
    bwNSSystemInternalQueueTimeMin                  Gauge32,
    bwNSSystemInternalQueueTimeMax                  Gauge32,
    bwNSSystemInternalQueueLengthCurrent            Gauge32,
    bwNSSystemInternalQueueLengthAvg                Gauge32,
    bwNSSystemInternalQueueLengthMax                Gauge32,
    bwNSSystemInternalQueueTimeMaxTimestampMSB      Gauge32,
    bwNSSystemInternalQueueLengthMaxTimestampMSB    Gauge32,
    bwNSSystemInternalQueueLengthMaxTimestampLSB    Gauge32,
    bwNSSystemInternalQueueTimeMaxTimestampLSB      Gauge32
}

bwNSSystemInternalQueueIndex OBJECT-TYPE
    SYNTAX      Unsigned32
    MAX-ACCESS  read-only
    STATUS      current
    DESCRIPTION 
        "This integer represents an index to an internal queue in the system."
    ::= { bwNSSystemInternalQueueEntry 1 }

bwNSSystemInternalQueueName OBJECT-TYPE
    SYNTAX      DisplayString
    MAX-ACCESS  read-only
    STATUS      current
    DESCRIPTION 
        "This string represents the name of an internal queue."
    ::= { bwNSSystemInternalQueueEntry 2 }

bwNSSystemInternalQueueSize OBJECT-TYPE
    SYNTAX      Counter32
    MAX-ACCESS  read-only
    STATUS      current
    DESCRIPTION 
        "The number of sample elements that the average, minimum and maximum holding time were calculated from."
    ::= { bwNSSystemInternalQueueEntry 3 }

bwNSSystemInternalQueueTimeAvg OBJECT-TYPE
    SYNTAX      Gauge32
    MAX-ACCESS  read-only
    STATUS      current
    DESCRIPTION 
        "The average queue holding time. Note that this value is in 1/1000 of millisec, i.e. divide by 1000 to get the value in milliseconds."
    ::= { bwNSSystemInternalQueueEntry 4 }

bwNSSystemInternalQueueTimeMin OBJECT-TYPE
    SYNTAX      Gauge32
    MAX-ACCESS  read-only
    STATUS      current
    DESCRIPTION 
        "The smallest queue sample holding time."
    ::= { bwNSSystemInternalQueueEntry 5 }

bwNSSystemInternalQueueTimeMax OBJECT-TYPE
    SYNTAX      Gauge32
    MAX-ACCESS  read-only
    STATUS      current
    DESCRIPTION 
        "The biggest queue sample holding time. Note that when the queue is not yet initialized or has just been reset the value of this gauge is set to a large negative value."
    ::= { bwNSSystemInternalQueueEntry 6 }

bwNSSystemInternalQueueLengthCurrent OBJECT-TYPE
    SYNTAX      Gauge32
    MAX-ACCESS  read-only
    STATUS      current
    DESCRIPTION 
        "The number of elements currently hold in the queue."
    ::= { bwNSSystemInternalQueueEntry 8 }

bwNSSystemInternalQueueLengthAvg OBJECT-TYPE
    SYNTAX      Gauge32
    MAX-ACCESS  read-only
    STATUS      current
    DESCRIPTION 
        "The average number of elements simultaneously held in the queue multiple by 1000. Divide by 1000 to get the value in units."
    ::= { bwNSSystemInternalQueueEntry 9 }

bwNSSystemInternalQueueLengthMax OBJECT-TYPE
    SYNTAX      Gauge32
    MAX-ACCESS  read-only
    STATUS      current
    DESCRIPTION 
        "The maximum number of elements simultaneously held in the queue multiple by 1000. Divide by 1000 to get the value in units."
    ::= { bwNSSystemInternalQueueEntry 10 }

bwNSSystemInternalQueueTimeMaxTimestampMSB OBJECT-TYPE
    SYNTAX      Gauge32
    MAX-ACCESS  read-only
    STATUS      current
    DESCRIPTION 
        "The most significant part of the timestamp (4 most significant bytes) of when bwSystemInternalQueueTimeMax was obtained."
    ::= { bwNSSystemInternalQueueEntry 12 }

bwNSSystemInternalQueueLengthMaxTimestampMSB OBJECT-TYPE
    SYNTAX      Gauge32
    MAX-ACCESS  read-only
    STATUS      current
    DESCRIPTION 
        "The most significant part of the timestamp (4 most significant bytes) of when bwSystemInternalQueueLengthMax was obtained."
    ::= { bwNSSystemInternalQueueEntry 13 }

bwNSSystemInternalQueueLengthMaxTimestampLSB OBJECT-TYPE
    SYNTAX      Gauge32
    MAX-ACCESS  read-only
    STATUS      current
    DESCRIPTION 
        "The least significant part of the timestamp (4 least significant bytes) of when bwSystemInternalQueueLengthMax was obtained."
    ::= { bwNSSystemInternalQueueEntry 14 }

bwNSSystemInternalQueueTimeMaxTimestampLSB OBJECT-TYPE
    SYNTAX      Gauge32
    MAX-ACCESS  read-only
    STATUS      current
    DESCRIPTION 
        "The least significant part of the timestamp (4 least significant bytes) of when bwSystemInternalQueueTimeMax was obtained."
    ::= { bwNSSystemInternalQueueEntry 15 }

overloadStats OBJECT IDENTIFIER
    ::= { system 13 }

bwNSCurrentCallOverloadZone OBJECT-TYPE
    SYNTAX      DisplayString
    MAX-ACCESS  read-only
    STATUS      current
    DESCRIPTION 
        "The current call related overload zone."
    ::= { overloadStats 1 }

bwNSNumCallYellowZoneOverloadTrans OBJECT-TYPE
    SYNTAX      Counter32
    MAX-ACCESS  read-write
    STATUS      current
    DESCRIPTION 
        "The number of times that the server has transitioned to the call-related yellow overload zone."
    ::= { overloadStats 2 }

bwNSNumCallRedZoneOverloadTrans OBJECT-TYPE
    SYNTAX      Counter32
    MAX-ACCESS  read-write
    STATUS      current
    DESCRIPTION 
        "The number of times that the server has transitioned to the call-related red overload zone."
    ::= { overloadStats 3 }

bwNSCurrentNonCallOverloadZone OBJECT-TYPE
    SYNTAX      DisplayString
    MAX-ACCESS  read-only
    STATUS      current
    DESCRIPTION 
        "The current non-call related overload zone."
    ::= { overloadStats 4 }

bwNSNumNonCallYellowZoneOverloadTrans OBJECT-TYPE
    SYNTAX      Counter32
    MAX-ACCESS  read-write
    STATUS      current
    DESCRIPTION 
        "The number of times that the server has transitioned to the non-call-related yellow overload zone."
    ::= { overloadStats 5 }

bwNSNumNonCallRedZoneOverloadTrans OBJECT-TYPE
    SYNTAX      Counter32
    MAX-ACCESS  read-write
    STATUS      current
    DESCRIPTION 
        "The number of times that the server has transitioned to the non-call-related red overload zone."
    ::= { overloadStats 6 }

bwNSNumDiscardedMessage OBJECT-TYPE
    SYNTAX      Counter32
    MAX-ACCESS  read-write
    STATUS      current
    DESCRIPTION 
        "The number of messages that were dropped from the SIP decoder queues."
    ::= { overloadStats 7 }

bwNSTimeLastDiscardedMessage OBJECT-TYPE
    SYNTAX      DisplayString
    MAX-ACCESS  read-write
    STATUS      current
    DESCRIPTION 
        "The last time a message was dropped from the SIP decoder queues."
    ::= { overloadStats 8 }

bwNSMemoryHighWaterMark OBJECT-TYPE
  SYNTAX      Gauge32
  MAX-ACCESS  read-only
  STATUS      current
  DESCRIPTION 
      "The high water mark for the heap size."
  ::= { overloadStats 9 }

bwNSMemoryHighWaterMarkTimeMSB OBJECT-TYPE
  SYNTAX      Gauge32
  MAX-ACCESS  read-only
  STATUS      current
  DESCRIPTION 
      "The most significant part of the timestamp (4 most significant bytes) of when bwMemoryHighWaterMark was obtained."
  ::= { overloadStats 10 }

bwNSMemoryHighWaterMarkTimeLSB OBJECT-TYPE
  SYNTAX      Gauge32
  MAX-ACCESS  read-only
  STATUS      current
  DESCRIPTION 
      "The least significant part of the timestamp (4 least significant bytes) of when bwMemoryHighWaterMark was obtained."
  ::= { overloadStats 11 }

bwNSOverloadStatsReset OBJECT-TYPE
  SYNTAX      Counter32
  MAX-ACCESS  read-write
  STATUS      current
  DESCRIPTION 
      "When set to a value other then 0, all the statistics stored under bwNSOverloadSampledDelayTable are reset to 0."
  ::= { overloadStats 12 }

bwNSOverloadStatsTable  OBJECT-TYPE
  SYNTAX      SEQUENCE OF BwNSOverloadStatsEntry
  MAX-ACCESS  not-accessible
  STATUS      current
  DESCRIPTION 
      "This table contains statistics about overload"
  ::= { overloadStats 13 }

bwNSOverloadStatsEntry OBJECT-TYPE
  SYNTAX      BwNSOverloadStatsEntry
  MAX-ACCESS  not-accessible
  STATUS      current
  DESCRIPTION 
      "This row contains the statistics for a given overload sampled in the system"
  INDEX       { bwNSOverloadSampledDataIndex }
  ::= { bwNSOverloadStatsTable 1 }

BwNSOverloadStatsEntry ::= SEQUENCE {
  bwNSOverloadSampledDataIndex               Unsigned32,
  bwNSOverloadSampledDataName                DisplayString,
  bwNSOverloadSampledDelayMin                Gauge32,
  bwNSOverloadSampledDelayAvg                Gauge32,
  bwNSOverloadSampledDelayMax                Gauge32,
  bwNSOverloadSampledDelayMaxTimeMSB         Gauge32,
  bwNSOverloadSampledDelayMaxTimeLSB         Gauge32,
  bwNSOverloadNumSamples                     Gauge32
}

bwNSOverloadSampledDataIndex OBJECT-TYPE
  SYNTAX      Unsigned32
  MAX-ACCESS  read-only
  STATUS      current
  DESCRIPTION 
      "This integer represents an index to an overload sample in the system."
  ::= { bwNSOverloadStatsEntry 1 }

bwNSOverloadSampledDataName OBJECT-TYPE
  SYNTAX      DisplayString
  MAX-ACCESS  read-only
  STATUS      current
  DESCRIPTION 
      "This string represents the name of an overload sample."
  ::= { bwNSOverloadStatsEntry 2 }

bwNSOverloadSampledDelayMin OBJECT-TYPE
  SYNTAX      Gauge32
  MAX-ACCESS  read-only
  STATUS      current
  DESCRIPTION 
      "This is the minimum sampled delay in milliseconds."
  ::= { bwNSOverloadStatsEntry 3 }

bwNSOverloadSampledDelayAvg OBJECT-TYPE
  SYNTAX      Gauge32
  MAX-ACCESS  read-only
  STATUS      current
  DESCRIPTION 
      "This is the average sampled delay in microseconds."
  ::= { bwNSOverloadStatsEntry 4 }

bwNSOverloadSampledDelayMax OBJECT-TYPE
  SYNTAX      Gauge32
  MAX-ACCESS  read-only
  STATUS      current
  DESCRIPTION 
      "This is the maximum sampled delay in milliseconds."
  ::= { bwNSOverloadStatsEntry 5 }

bwNSOverloadSampledDelayMaxTimeMSB OBJECT-TYPE
  SYNTAX      Gauge32
  MAX-ACCESS  read-only
  STATUS      current
  DESCRIPTION 
      "The most significant part of the timestamp (4 most significant bytes) of when bwNSOverloadSampledDelayMax was obtained."
  ::= { bwNSOverloadStatsEntry 6 }

bwNSOverloadSampledDelayMaxTimeLSB OBJECT-TYPE
  SYNTAX      Gauge32
  MAX-ACCESS  read-only
  STATUS      current
  DESCRIPTION 
      "The least significant part of the timestamp (4 least significant bytes) of when bwNSOverloadSampledDelayMax was obtained."
  ::= { bwNSOverloadStatsEntry 7 }

bwNSOverloadNumSamples OBJECT-TYPE
  SYNTAX      Gauge32
  MAX-ACCESS  read-only
  STATUS      current
  DESCRIPTION 
      "The total number of overload samples processed."
  ::= { bwNSOverloadStatsEntry 8 }

processing OBJECT IDENTIFIER
    ::= { nsExecutionServer 2 }

policies OBJECT IDENTIFIER
    ::= { processing 3 }

publicPolicyStatTable OBJECT-TYPE
    SYNTAX      SEQUENCE OF PublicPolicyStatEntry
    MAX-ACCESS  not-accessible
    STATUS      current
    DESCRIPTION 
        "This table stores all of the public policies standard measurements."
    ::= { policies 1 }

publicPolicyStatEntry OBJECT-TYPE
    SYNTAX      PublicPolicyStatEntry
    MAX-ACCESS  not-accessible
    STATUS      current
    DESCRIPTION 
        "Point of entry for entries to table publicPolicyStatTable."
    INDEX       { pubPolStatID }
    ::= { publicPolicyStatTable 1 }

PublicPolicyStatEntry ::= SEQUENCE {
    pubPolStatID                    Unsigned32,
    pubPolStatPolicyName            DisplayString,
    pubPolStatNbInstances           Gauge32,
    pubPolStatNbRequests            Counter32,
    pubPolStatNbRequestsFailures    Counter32,
    pubPolStatNbRequestsResults     Counter32
}

pubPolStatID OBJECT-TYPE
    SYNTAX      Unsigned32
    MAX-ACCESS  not-accessible
    STATUS      current
    DESCRIPTION 
        "Description"
    ::= { publicPolicyStatEntry 1 }

pubPolStatPolicyName OBJECT-TYPE
    SYNTAX      DisplayString
    MAX-ACCESS  read-only
    STATUS      current
    DESCRIPTION 
        "the name of the policy"
    ::= { publicPolicyStatEntry 2 }

pubPolStatNbInstances OBJECT-TYPE
    SYNTAX      Gauge32
    MAX-ACCESS  read-only
    STATUS      current
    DESCRIPTION 
        "the number of instances of that policy in the system"
    ::= { publicPolicyStatEntry 3 }

pubPolStatNbRequests OBJECT-TYPE
    SYNTAX      Counter32
    MAX-ACCESS  read-write
    STATUS      current
    DESCRIPTION 
        "the total number of requests processed by that policy"
    ::= { publicPolicyStatEntry 4 }

pubPolStatNbRequestsFailures OBJECT-TYPE
    SYNTAX      Counter32
    MAX-ACCESS  read-write
    STATUS      current
    DESCRIPTION 
        "the total number of calls that were sent to treatment by this  policy"
    ::= { publicPolicyStatEntry 5 }

pubPolStatNbRequestsResults OBJECT-TYPE
    SYNTAX      Counter32
    MAX-ACCESS  read-write
    STATUS      current
    DESCRIPTION 
        "the total number of calls for which that policy has provided a route list"
    ::= { publicPolicyStatEntry 6 }

privatePolicyStatTable OBJECT-TYPE
    SYNTAX      SEQUENCE OF PrivatePolicyStatEntry
    MAX-ACCESS  not-accessible
    STATUS      current
    DESCRIPTION 
        "This table stores all of the private policies standard measurements."
    ::= { policies 2 }

privatePolicyStatEntry OBJECT-TYPE
    SYNTAX      PrivatePolicyStatEntry
    MAX-ACCESS  not-accessible
    STATUS      current
    DESCRIPTION 
        "Point of entry for entries to table privatePolicyStatTable."
    INDEX       { privPolStatID }
    ::= { privatePolicyStatTable 1 }

PrivatePolicyStatEntry ::= SEQUENCE {
    privPolStatID                   Unsigned32,
    privPolStatEnterpriseName       DisplayString,
    privPolStatPolicyName           DisplayString,
    privPolStatNbRequests           Counter32,
    privPolStatNbRequestsFailures   Counter32,
    privPolStatNbRequestsResults    Counter32
}

privPolStatID OBJECT-TYPE
    SYNTAX      Unsigned32
    MAX-ACCESS  not-accessible
    STATUS      current
    DESCRIPTION 
        "Description"
    ::= { privatePolicyStatEntry 1 }

privPolStatEnterpriseName OBJECT-TYPE
    SYNTAX      DisplayString
    MAX-ACCESS  read-only
    STATUS      current
    DESCRIPTION 
        "the name of the enterprise to which the policy is assigned"
    ::= { privatePolicyStatEntry 2 }

privPolStatPolicyName OBJECT-TYPE
    SYNTAX      DisplayString
    MAX-ACCESS  read-only
    STATUS      current
    DESCRIPTION 
        "the name of the policy"
    ::= { privatePolicyStatEntry 3 }

privPolStatNbRequests OBJECT-TYPE
    SYNTAX      Counter32
    MAX-ACCESS  read-write
    STATUS      current
    DESCRIPTION 
        "the total number of requests processed by that policy"
    ::= { privatePolicyStatEntry 4 }

privPolStatNbRequestsFailures OBJECT-TYPE
    SYNTAX      Counter32
    MAX-ACCESS  read-write
    STATUS      current
    DESCRIPTION 
        "the total number of calls that were sent to treatment by this policy"
    ::= { privatePolicyStatEntry 5 }

privPolStatNbRequestsResults OBJECT-TYPE
    SYNTAX      Counter32
    MAX-ACCESS  read-write
    STATUS      current
    DESCRIPTION 
        "the total number of calls for which that policy has provided a route list"
    ::= { privatePolicyStatEntry 6 }

policyInfoTable OBJECT-TYPE
    SYNTAX      SEQUENCE OF PolicyInfoEntry
    MAX-ACCESS  not-accessible
    STATUS      current
    DESCRIPTION 
        "The table allow for a policy to implement additional custom measurements. Both private and public policies can extend this table."
    ::= { policies 3 }

policyInfoEntry OBJECT-TYPE
    SYNTAX      PolicyInfoEntry
    MAX-ACCESS  not-accessible
    STATUS      current
    DESCRIPTION 
        "Point of entry for entries to table policyInfoTable."
    INDEX       { polInfoID }
    ::= { policyInfoTable 1 }

PolicyInfoEntry ::= SEQUENCE {
    polInfoID               Unsigned32,
    polInfoEnterpriseName   DisplayString,
    polInfoPolicyName       DisplayString,
    polInfoInfoName         DisplayString,
    polInfoNbOccurences     Counter32
}

polInfoID OBJECT-TYPE
    SYNTAX      Unsigned32
    MAX-ACCESS  not-accessible
    STATUS      current
    DESCRIPTION 
        "Description"
    ::= { policyInfoEntry 1 }

polInfoEnterpriseName OBJECT-TYPE
    SYNTAX      DisplayString
    MAX-ACCESS  read-only
    STATUS      current
    DESCRIPTION 
        "the name of the enterprise for which the policy count applies"
    ::= { policyInfoEntry 2 }

polInfoPolicyName OBJECT-TYPE
    SYNTAX      DisplayString
    MAX-ACCESS  read-only
    STATUS      current
    DESCRIPTION 
        "the name of the policy for which the policy count applies"
    ::= { policyInfoEntry 3 }

polInfoInfoName OBJECT-TYPE
    SYNTAX      DisplayString
    MAX-ACCESS  read-only
    STATUS      current
    DESCRIPTION 
        "the information monitored"
    ::= { policyInfoEntry 4 }

polInfoNbOccurences OBJECT-TYPE
    SYNTAX      Counter32
    MAX-ACCESS  read-write
    STATUS      current
    DESCRIPTION 
        "total number of occurrences of this information/policy"
    ::= { policyInfoEntry 5 }

bwNbPolicyRequests OBJECT-TYPE
    SYNTAX      Counter32
    MAX-ACCESS  read-write
    STATUS      current
    DESCRIPTION 
        "This counter reflects the total number of Policy processing requests received by BroadWorks."
    ::= { policies 4 }

bwNbPolicyRequestFailures OBJECT-TYPE
    SYNTAX      Counter32
    MAX-ACCESS  read-write
    STATUS      current
    DESCRIPTION 
        "This counter reflects the total number of Policy processing request failures received by BroadWorks."
    ::= { policies 5 }

neStatTable OBJECT-TYPE
    SYNTAX      SEQUENCE OF NeStatEntry
    MAX-ACCESS  not-accessible
    STATUS      current
    DESCRIPTION 
        "This table implements generic per Network Element measurements."
    ::= { processing 4 }

neStatEntry OBJECT-TYPE
    SYNTAX      NeStatEntry
    MAX-ACCESS  not-accessible
    STATUS      current
    DESCRIPTION 
        "Point of entry for entries to table neStatTable."
    INDEX       { neStatID }
    ::= { neStatTable 1 }

NeStatEntry ::= SEQUENCE {
    neStatID                        Unsigned32,
    neStatName                      DisplayString,
    neStatNbSIPRequests             Counter32,
    neStatNbSIPRequestsFailures     Counter32,
    neStatNbMSSRequests             Counter32,
    neStatNbMSSRequestsFailures     Counter32
}

neStatID OBJECT-TYPE
    SYNTAX      Unsigned32
    MAX-ACCESS  not-accessible
    STATUS      current
    DESCRIPTION 
        "Description"
    ::= { neStatEntry 1 }

neStatName OBJECT-TYPE
    SYNTAX      DisplayString
    MAX-ACCESS  read-only
    STATUS      current
    DESCRIPTION 
        "name of the network element that sent a request to the network server"
    ::= { neStatEntry 2 }

neStatNbSIPRequests OBJECT-TYPE
    SYNTAX      Counter32
    MAX-ACCESS  read-write
    STATUS      current
    DESCRIPTION 
        "total number of SIP requests coming in"
    ::= { neStatEntry 3 }

neStatNbSIPRequestsFailures OBJECT-TYPE
    SYNTAX      Counter32
    MAX-ACCESS  read-write
    STATUS      current
    DESCRIPTION 
        "total number of SIP requests which resulted in a treatment "
    ::= { neStatEntry 4 }

neStatNbMSSRequests OBJECT-TYPE
    SYNTAX      Counter32
    MAX-ACCESS  read-write
    STATUS      current
    DESCRIPTION 
        "total number of MSS requests coming in"
    ::= { neStatEntry 5 }

neStatNbMSSRequestsFailures OBJECT-TYPE
    SYNTAX      Counter32
    MAX-ACCESS  read-write
    STATUS      current
    DESCRIPTION 
        "total number of MSS requests resulting in an error"
    ::= { neStatEntry 6 }

errorStatTable OBJECT-TYPE
    SYNTAX      SEQUENCE OF ErrorStatEntry
    MAX-ACCESS  not-accessible
    STATUS      current
    DESCRIPTION 
        "This table implements measurements for all the error codes defined in the system."
    ::= { processing 5 }

errorStatEntry OBJECT-TYPE
    SYNTAX      ErrorStatEntry
    MAX-ACCESS  not-accessible
    STATUS      current
    DESCRIPTION 
        "Point of entry for entries to table errorStatTable."
    INDEX       { errStatID }
    ::= { errorStatTable 1 }

ErrorStatEntry ::= SEQUENCE {
    errStatID               Unsigned32,
    errStatName             DisplayString,
    errStatNbOccurences     Counter32
}

errStatID OBJECT-TYPE
    SYNTAX      Unsigned32
    MAX-ACCESS  not-accessible
    STATUS      current
    DESCRIPTION 
        "Description"
    ::= { errorStatEntry 1 }

errStatName OBJECT-TYPE
    SYNTAX      DisplayString
    MAX-ACCESS  read-only
    STATUS      current
    DESCRIPTION 
        "code name of the network server error"
    ::= { errorStatEntry 2 }

errStatNbOccurences OBJECT-TYPE
    SYNTAX      Counter32
    MAX-ACCESS  read-write
    STATUS      current
    DESCRIPTION 
        "total number of times this error occurred"
    ::= { errorStatEntry 3 }

bwNSCallpCallsPerSecond OBJECT-TYPE
    SYNTAX      Gauge32
    MAX-ACCESS  read-only
    STATUS      current
    DESCRIPTION 
        "This gauge measures the rate at which call attempts occur.  It uses the timestamps of up to the last 100 calls attempts to calculate the rate."
    ::= { processing 6 }

carrierStatTable OBJECT-TYPE
    SYNTAX      SEQUENCE OF CarrierStatEntry
    MAX-ACCESS  not-accessible
    STATUS      current
    DESCRIPTION 
        "This table stores the statistics for all the carriers used to route calls in the system."
    ::= { processing 7 }

bwNSCallpNumberOfActiveSessions OBJECT-TYPE
    SYNTAX      Gauge32
    MAX-ACCESS  read-only
    STATUS      current
    DESCRIPTION 
        "This is the number of call processing sessions currently active in the system."
    ::= { processing 8 }

carrierStatEntry OBJECT-TYPE
    SYNTAX      CarrierStatEntry
    MAX-ACCESS  not-accessible
    STATUS      current
    DESCRIPTION 
        "Point of entry for entries to table carrierStatTable."
    INDEX       { bwCarrierStatID }
    ::= { carrierStatTable 1 }

CarrierStatEntry ::= SEQUENCE {
    bwCarrierStatID                 Unsigned32,
    bwCarrierName                   DisplayString,
    bwCarrierCic                    DisplayString,
    bwCarrierNbIntraLataCalls       Counter32,
    bwCarrierNbInterLataCalls       Counter32,
    bwCarrierNbInternationalCalls   Counter32
}

bwCarrierStatID OBJECT-TYPE
    SYNTAX      Unsigned32
    MAX-ACCESS  not-accessible
    STATUS      current
    DESCRIPTION 
        "Unique identifier for a carrier in the system."
    ::= { carrierStatEntry 1 }

bwCarrierName OBJECT-TYPE
    SYNTAX      DisplayString
    MAX-ACCESS  read-only
    STATUS      current
    DESCRIPTION 
        "The name of a carrier defined on the network server."
    ::= { carrierStatEntry 2 }

bwCarrierCic OBJECT-TYPE
    SYNTAX      DisplayString
    MAX-ACCESS  read-only
    STATUS      current
    DESCRIPTION 
        "A CIC used for a given carrier in the system."
    ::= { carrierStatEntry 3 }

bwCarrierNbIntraLataCalls OBJECT-TYPE
    SYNTAX      Counter32
    MAX-ACCESS  read-write
    STATUS      current
    DESCRIPTION 
        "This counter shall be incremented each time a carrier is used to carry an international call."
    ::= { carrierStatEntry 4 }

bwCarrierNbInterLataCalls OBJECT-TYPE
    SYNTAX      Counter32
    MAX-ACCESS  read-write
    STATUS      current
    DESCRIPTION 
        "This counter shall be incremented each time a carrier is used to carry an inter-LATA call."
    ::= { carrierStatEntry 5 }

bwCarrierNbInternationalCalls OBJECT-TYPE
    SYNTAX      Counter32
    MAX-ACCESS  read-write
    STATUS      current
    DESCRIPTION 
        "This counter shall be incremented each time a carrier is used to carry an intra-LATA call."
    ::= { carrierStatEntry 6 }

protocol OBJECT IDENTIFIER
    ::= { nsExecutionServer 3 }

sip OBJECT IDENTIFIER
    ::= { protocol 1 }

bwNSSipStatsInviteIns OBJECT-TYPE
    SYNTAX      Counter32
    MAX-ACCESS  read-write
    STATUS      current
    DESCRIPTION 
        "This counter reflects the total number of INVITE requests received by BroadWorks."
    ::= { sip 1 }

bwNSSipStatsAckIns OBJECT-TYPE
    SYNTAX      Counter32
    MAX-ACCESS  read-write
    STATUS      current
    DESCRIPTION 
        "This counter reflects the total number of ACK requests received by BroadWorks."
    ::= { sip 2 }

bwNSSipStatsInviteResponsesTable OBJECT-TYPE
    SYNTAX      SEQUENCE OF BwNSSipStatsInviteResponsesEntry
    MAX-ACCESS  not-accessible
    STATUS      current
    DESCRIPTION 
        "This table contains the counters for all SIP responses to the Invite requests sent by BroadWorks. Each counter is a 32-Bit counter. The response code is used to index into the table. Here are all the response codes:  302, 400, 401, 402, 403, 404, 405, 406, 407, 408, 409, 410, 411, 413, 414, 415, 420, 480, 481, 482, 483, 484, 485, 486, 487"
    ::= { sip 3 }

bwNSSipStatsInviteResponsesEntry OBJECT-TYPE
    SYNTAX      BwNSSipStatsInviteResponsesEntry
    MAX-ACCESS  not-accessible
    STATUS      current
    DESCRIPTION 
        "This row contains information on a particular SIP status code sent in response to an Invite"
    INDEX       { bwNSSipStatsInviteResponseCodeValue }
    ::= { bwNSSipStatsInviteResponsesTable 1 }

BwNSSipStatsInviteResponsesEntry ::= SEQUENCE {
    bwNSSipStatsInviteResponseCodeValue     Integer32,
    bwNSSipStatsInviteResponseOuts          Counter32
}

bwNSSipStatsInviteResponseCodeValue OBJECT-TYPE
    SYNTAX      Integer32 (100..999)
    MAX-ACCESS  not-accessible
    STATUS      current
    DESCRIPTION 
        "This integer represents a SIP status code.  The rest of the information in this row is related to this value."
    ::= { bwNSSipStatsInviteResponsesEntry 1 }

bwNSSipStatsInviteResponseOuts OBJECT-TYPE
    SYNTAX      Counter32
    MAX-ACCESS  read-write
    STATUS      current
    DESCRIPTION 
        "This counter represents the number of SIP responses sent in response to an Invite"
    ::= { bwNSSipStatsInviteResponsesEntry 3 }

bwNSSipStatsCancelIns OBJECT-TYPE
    SYNTAX      Counter32
    MAX-ACCESS  read-write
    STATUS      current
    DESCRIPTION 
        "This counter reflects the total number of CANCEL requests received by BroadWorks."
    ::= { sip 4 }

bwNSSipStatsRegisterIns OBJECT-TYPE
    SYNTAX      Counter32
    MAX-ACCESS  read-write
    STATUS      current
    DESCRIPTION 
        "This counter reflects the total number of REGISTER requests received by BroadWorks."
    ::= { sip 5 }

bwNSSipStatsNotifyIns OBJECT-TYPE
    SYNTAX      Counter32
    MAX-ACCESS  read-write
    STATUS      current
    DESCRIPTION 
        "This counter reflects the total number of INFO requests received by BroadWorks"
    ::= { sip 6 }

bwNSSipStatsSubscribeIns OBJECT-TYPE
    SYNTAX      Counter32
    MAX-ACCESS  read-write
    STATUS      current
    DESCRIPTION 
        "This counter reflects the total number of SUBSCRIBE message that have been received at the AS."
    ::= { sip 7 }

bwNSSipStatsMessageIns OBJECT-TYPE
    SYNTAX      Counter32
    MAX-ACCESS  read-write
    STATUS      current
    DESCRIPTION 
        "This counter reflects the total number of MESSAGE message that have been received at the AS."
    ::= { sip 8 }

bwNSSipStatsInfoIns OBJECT-TYPE
    SYNTAX      Counter32
    MAX-ACCESS  read-write
    STATUS      current
    DESCRIPTION 
        "This counter reflects the total number of INFO requests received by BroadWorks"
    ::= { sip 9 }

bwNSSipStatsOptionsIns OBJECT-TYPE
    SYNTAX      Counter32
    MAX-ACCESS  read-write
    STATUS      current
    DESCRIPTION 
        "This counter reflects the total number of OPTIONS requests received by BroadWorks."
    ::= { sip 10 }

bwNSSipStatsOptionsResponsesTable OBJECT-TYPE
    SYNTAX      SEQUENCE OF BwNSSipStatsOptionsResponsesEntry
    MAX-ACCESS  not-accessible
    STATUS      current
    DESCRIPTION 
        "This table contains the counters for all SIP responses to the Options requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
    ::= { sip 11 }

bwNSSipStatsOptionsResponsesEntry OBJECT-TYPE
    SYNTAX      BwNSSipStatsOptionsResponsesEntry
    MAX-ACCESS  not-accessible
    STATUS      current
    DESCRIPTION 
        "This row contains information on a particular SIP status code received or sent in response to a Options"
    INDEX       { bwNSSipStatsOptionsResponseCodeValue }
    ::= { bwNSSipStatsOptionsResponsesTable 1 }

BwNSSipStatsOptionsResponsesEntry ::= SEQUENCE {
    bwNSSipStatsOptionsResponseCodeValue    Integer32,
    bwNSSipStatsOptionsResponseIns          Counter32,
    bwNSSipStatsOptionsResponseOuts         Counter32
}

bwNSSipStatsOptionsResponseCodeValue OBJECT-TYPE
    SYNTAX      Integer32 (100..999)
    MAX-ACCESS  not-accessible
    STATUS      current
    DESCRIPTION 
        "This integer represents a SIP status code.  The rest of the information in this row is related to this value."
    ::= { bwNSSipStatsOptionsResponsesEntry 1 }

bwNSSipStatsOptionsResponseIns OBJECT-TYPE
    SYNTAX      Counter32
    MAX-ACCESS  read-write
    STATUS      current
    DESCRIPTION 
        "This counter represents the number of SIP responses received in response to an Options"
    ::= { bwNSSipStatsOptionsResponsesEntry 2 }

bwNSSipStatsOptionsResponseOuts OBJECT-TYPE
    SYNTAX      Counter32
    MAX-ACCESS  read-write
    STATUS      current
    DESCRIPTION 
        "This counter represents the number of SIP responses sent in response to an Options"
    ::= { bwNSSipStatsOptionsResponsesEntry 3 }

bwNSSipStatsRegisterResponsesTable OBJECT-TYPE
    SYNTAX      SEQUENCE OF BwNSSipStatsRegisterResponsesEntry
    MAX-ACCESS  not-accessible
    STATUS      current
    DESCRIPTION 
        "This table contains the counters for all SIP responses to the Register requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
    ::= { sip 12 }

bwNSSipStatsRegisterResponsesEntry OBJECT-TYPE
    SYNTAX      BwNSSipStatsRegisterResponsesEntry
    MAX-ACCESS  not-accessible
    STATUS      current
    DESCRIPTION 
        "This row contains information on a particular SIP status code received or sent in response to a Register"
    INDEX       { bwNSSipStatsRegisterResponseCodeValue }
    ::= { bwNSSipStatsRegisterResponsesTable 1 }

BwNSSipStatsRegisterResponsesEntry ::= SEQUENCE {
    bwNSSipStatsRegisterResponseCodeValue   Integer32,
    bwNSSipStatsRegisterResponseIns         Counter32,
    bwNSSipStatsRegisterResponseOuts        Counter32
}

bwNSSipStatsRegisterResponseCodeValue OBJECT-TYPE
    SYNTAX      Integer32 (100..999)
    MAX-ACCESS  not-accessible
    STATUS      current
    DESCRIPTION 
        "This integer represents a SIP status code.  The rest of the information in this row is related to this value."
    ::= { bwNSSipStatsRegisterResponsesEntry 1 }

bwNSSipStatsRegisterResponseIns OBJECT-TYPE
    SYNTAX      Counter32
    MAX-ACCESS  read-write
    STATUS      current
    DESCRIPTION 
        "This counter represents the number of SIP responses received in response to a Register"
    ::= { bwNSSipStatsRegisterResponsesEntry 2 }

bwNSSipStatsRegisterResponseOuts OBJECT-TYPE
    SYNTAX      Counter32
    MAX-ACCESS  read-write
    STATUS      current
    DESCRIPTION 
        "This counter represents the number of SIP responses sent in response to a Register"
    ::= { bwNSSipStatsRegisterResponsesEntry 3 }

bwNSSipStatsInfoResponsesTable OBJECT-TYPE
    SYNTAX      SEQUENCE OF BwNSSipStatsInfoResponsesEntry
    MAX-ACCESS  not-accessible
    STATUS      current
    DESCRIPTION 
        "This table contains the counters for all SIP responses to the Info requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
    ::= { sip 13 }

bwNSSipStatsInfoResponsesEntry OBJECT-TYPE
    SYNTAX      BwNSSipStatsInfoResponsesEntry
    MAX-ACCESS  not-accessible
    STATUS      current
    DESCRIPTION 
        "This row contains information on a particular SIP status code received or sent in response to an Info"
    INDEX       { bwNSSipStatsInfoResponseCodeValue }
    ::= { bwNSSipStatsInfoResponsesTable 1 }

BwNSSipStatsInfoResponsesEntry ::= SEQUENCE {
    bwNSSipStatsInfoResponseCodeValue   Integer32,
    bwNSSipStatsInfoResponseIns         Counter32,
    bwNSSipStatsInfoResponseOuts        Counter32
}

bwNSSipStatsInfoResponseCodeValue OBJECT-TYPE
    SYNTAX      Integer32 (100..999)
    MAX-ACCESS  not-accessible
    STATUS      current
    DESCRIPTION 
        "This integer represents a SIP status code.  The rest of the information in this row is related to this value."
    ::= { bwNSSipStatsInfoResponsesEntry 1 }

bwNSSipStatsInfoResponseIns OBJECT-TYPE
    SYNTAX      Counter32
    MAX-ACCESS  read-write
    STATUS      current
    DESCRIPTION 
        "This counter represents the number of SIP responses received in response to an Info"
    ::= { bwNSSipStatsInfoResponsesEntry 2 }

bwNSSipStatsInfoResponseOuts OBJECT-TYPE
    SYNTAX      Counter32
    MAX-ACCESS  read-write
    STATUS      current
    DESCRIPTION 
        "This counter represents the number of SIP responses sent in response to an Info"
    ::= { bwNSSipStatsInfoResponsesEntry 3 }

bwNSSipStatsNotifyResponsesTable OBJECT-TYPE
    SYNTAX      SEQUENCE OF BwNSSipStatsNotifyResponsesEntry
    MAX-ACCESS  not-accessible
    STATUS      current
    DESCRIPTION 
        "This table contains the counters for all SIP responses to the Notify requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
    ::= { sip 14 }

bwNSSipStatsNotifyResponsesEntry OBJECT-TYPE
    SYNTAX      BwNSSipStatsNotifyResponsesEntry
    MAX-ACCESS  not-accessible
    STATUS      current
    DESCRIPTION 
        "This row contains information on a particular SIP status code received or sent in response to an Notify"
    INDEX       { bwNSSipStatsNotifyResponseCodeValue }
    ::= { bwNSSipStatsNotifyResponsesTable 1 }

BwNSSipStatsNotifyResponsesEntry ::= SEQUENCE {
    bwNSSipStatsNotifyResponseCodeValue     Integer32,
    bwNSSipStatsNotifyResponseIns           Counter32,
    bwNSSipStatsNotifyResponseOuts          Counter32
}

bwNSSipStatsNotifyResponseCodeValue OBJECT-TYPE
    SYNTAX      Integer32 (100..999)
    MAX-ACCESS  not-accessible
    STATUS      current
    DESCRIPTION 
        "This integer represents a SIP status code.  The rest of the information in this row is related to this value."
    ::= { bwNSSipStatsNotifyResponsesEntry 1 }

bwNSSipStatsNotifyResponseIns OBJECT-TYPE
    SYNTAX      Counter32
    MAX-ACCESS  read-write
    STATUS      current
    DESCRIPTION 
        "This counter represents the number of SIP responses received in response to a Notify"
    ::= { bwNSSipStatsNotifyResponsesEntry 2 }

bwNSSipStatsNotifyResponseOuts OBJECT-TYPE
    SYNTAX      Counter32
    MAX-ACCESS  read-write
    STATUS      current
    DESCRIPTION 
        "This counter represents the number of SIP responses sent in response to a Notify"
    ::= { bwNSSipStatsNotifyResponsesEntry 3 }

bwNSSipStatsSubscribeResponsesTable OBJECT-TYPE
    SYNTAX      SEQUENCE OF BwNSSipStatsSubscribeResponsesEntry
    MAX-ACCESS  not-accessible
    STATUS      current
    DESCRIPTION 
        "This table contains the counters for all SIP responses to the Subscribe requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
    ::= { sip 15 }

bwNSSipStatsSubscribeResponsesEntry OBJECT-TYPE
    SYNTAX      BwNSSipStatsSubscribeResponsesEntry
    MAX-ACCESS  not-accessible
    STATUS      current
    DESCRIPTION 
        "This row contains information on a particular SIP status code received or sent in response to a Subscribe"
    INDEX       { bwNSSipStatsSubscribeResponseCodeValue }
    ::= { bwNSSipStatsSubscribeResponsesTable 1 }

BwNSSipStatsSubscribeResponsesEntry ::= SEQUENCE {
    bwNSSipStatsSubscribeResponseCodeValue  Integer32,
    bwNSSipStatsSubscribeResponseIns        Counter32,
    bwNSSipStatsSubscribeResponseOuts       Counter32
}

bwNSSipStatsSubscribeResponseCodeValue OBJECT-TYPE
    SYNTAX      Integer32 (100..999)
    MAX-ACCESS  not-accessible
    STATUS      current
    DESCRIPTION 
        "This integer represents a SIP status code.  The rest of the information in this row is related to this value."
    ::= { bwNSSipStatsSubscribeResponsesEntry 1 }

bwNSSipStatsSubscribeResponseIns OBJECT-TYPE
    SYNTAX      Counter32
    MAX-ACCESS  read-write
    STATUS      current
    DESCRIPTION 
        "This counter represents the number of SIP responses received in response to a Subscribe"
    ::= { bwNSSipStatsSubscribeResponsesEntry 2 }

bwNSSipStatsSubscribeResponseOuts OBJECT-TYPE
    SYNTAX      Counter32
    MAX-ACCESS  read-write
    STATUS      current
    DESCRIPTION 
        "This counter represents the number of SIP responses sent in response to a Subscribe"
    ::= { bwNSSipStatsSubscribeResponsesEntry 3 }

bwNSSipStatsMessageResponsesTable OBJECT-TYPE
    SYNTAX      SEQUENCE OF BwNSSipStatsMessageResponsesEntry
    MAX-ACCESS  not-accessible
    STATUS      current
    DESCRIPTION 
        "This table contains the counters for all SIP responses to the Message requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
    ::= { sip 16 }

bwNSSipStatsMessageResponsesEntry OBJECT-TYPE
    SYNTAX      BwNSSipStatsMessageResponsesEntry
    MAX-ACCESS  not-accessible
    STATUS      current
    DESCRIPTION 
        "This row contains information on a particular SIP status code received or sent in response to a Message"
    INDEX       { bwNSSipStatsMessageResponseCodeValue }
    ::= { bwNSSipStatsMessageResponsesTable 1 }

BwNSSipStatsMessageResponsesEntry ::= SEQUENCE {
    bwNSSipStatsMessageResponseCodeValue    Integer32,
    bwNSSipStatsMessageResponseIns          Counter32,
    bwNSSipStatsMessageResponseOuts         Counter32
}

bwNSSipStatsMessageResponseCodeValue OBJECT-TYPE
    SYNTAX      Integer32 (100..999)
    MAX-ACCESS  not-accessible
    STATUS      current
    DESCRIPTION 
        "This integer represents a SIP status code.  The rest of the information in this row is related to this value."
    ::= { bwNSSipStatsMessageResponsesEntry 1 }

bwNSSipStatsMessageResponseIns OBJECT-TYPE
    SYNTAX      Counter32
    MAX-ACCESS  read-write
    STATUS      current
    DESCRIPTION 
        "This counter represents the number of SIP responses received in response to a Message"
    ::= { bwNSSipStatsMessageResponsesEntry 2 }

bwNSSipStatsMessageResponseOuts OBJECT-TYPE
    SYNTAX      Counter32
    MAX-ACCESS  read-write
    STATUS      current
    DESCRIPTION 
        "This counter represents the number of SIP responses sent in response to a Message"
    ::= { bwNSSipStatsMessageResponsesEntry 3 }

bwNSSipStatsFailures OBJECT-TYPE
    SYNTAX      Counter32
    MAX-ACCESS  read-write
    STATUS      current
    DESCRIPTION 
        "This counter reflects the total number of request failures, i.e. the number of responses that were not 302s"
    ::= { sip 17 }

bwNSSipStatsActiveTcpConnections OBJECT-TYPE
    SYNTAX      Gauge32
    MAX-ACCESS  read-only
    STATUS      current
    DESCRIPTION 
        "This gauge is incremented whenever a SIP TCP connection is established.   It decremented whenever a connection is closed."
    ::= { sip 18 }

bwNSSipStatsTcpIns OBJECT-TYPE
    SYNTAX      Counter32
    MAX-ACCESS  read-write
    STATUS      current
    DESCRIPTION 
        "This counter is incremented whenever a SIP message is received via TCP."
    ::= { sip 19 }

bwNSSipStatsTcpOuts OBJECT-TYPE
    SYNTAX      Counter32
    MAX-ACCESS  read-write
    STATUS      current
    DESCRIPTION 
        "This counter is incremented whenever a SIP message is sent via TCP."
    ::= { sip 20 }

bwNSSipStatsTcpFailures OBJECT-TYPE
    SYNTAX      Counter32
    MAX-ACCESS  read-write
    STATUS      current
    DESCRIPTION 
        "This counter is incremented whenever a SIP message was attempted to be sent via TCP but failed."
    ::= { sip 21 }

bwNSSipStatsUdpIns OBJECT-TYPE
    SYNTAX      Counter32
    MAX-ACCESS  read-write
    STATUS      current
    DESCRIPTION 
        "This counter is incremented whenever a SIP message is received via UDP."
    ::= { sip 22 }

bwNSSipStatsUdpOuts OBJECT-TYPE
    SYNTAX      Counter32
    MAX-ACCESS  read-write
    STATUS      current
    DESCRIPTION 
        "This counter is incremented whenever a SIP message is sent via UDP."
    ::= { sip 23 }

bwNSSIPReclaimedStaleTcpConnections OBJECT-TYPE
    SYNTAX      Counter32
    MAX-ACCESS  read-write
    STATUS      current
    DESCRIPTION 
        "This counter is incremented every time a SIP TCP connection is reclaimed because it is stale."
    ::= { sip 24 }

congestionManagement OBJECT IDENTIFIER
    ::= { sip 25 }

bwNSCongestionManagementNeighborTable OBJECT-TYPE
    SYNTAX      SEQUENCE OF BwNSCongestionManagementNeighborEntry
    MAX-ACCESS  not-accessible
    STATUS      current
    DESCRIPTION 
        "This table contains congestion management information associated to neighbors."
    ::= { congestionManagement 1 }

bwNSCongestionManagementNeighborEntry OBJECT-TYPE
    SYNTAX      BwNSCongestionManagementNeighborEntry
    MAX-ACCESS  not-accessible
    STATUS      current
    DESCRIPTION 
        "This row contains congestion management information related to a neighbor."
    INDEX       { bwNSCongestionManagementNeighborIndex }
    ::= { bwNSCongestionManagementNeighborTable 1 }

BwNSCongestionManagementNeighborEntry ::= SEQUENCE {
    bwNSCongestionManagementNeighborIndex                   Unsigned32,
    bwNSCongestionManagementNeighborIpAddress               DisplayString,
    bwNSCongestionManagementNeighborInviteIn                Counter32,
    bwNSCongestionManagementNeighborRegisterIn              Counter32,
    bwNSCongestionManagementNeighborOptionsIn               Counter32,
    bwNSCongestionManagementNeighborOptionsOut              Counter32,
    bwNSCongestionManagementNeighborSubscribeNotifyIn       Counter32,
    bwNSCongestionManagementNeighbor5xxIn                   Counter32,
    bwNSCongestionManagementNeighborCallpRequestInRate      Gauge32,
    bwNSCongestionManagementNeighborNonCallpRequestInRate   Gauge32,
    bwNSCongestionManagementNeighborState                   DisplayString,
    bwNSCongestionManagementNeighborCapability              DisplayString
}

bwNSCongestionManagementNeighborIndex OBJECT-TYPE
    SYNTAX      Unsigned32
    MAX-ACCESS  not-accessible
    STATUS      current
    DESCRIPTION 
        "Index to a neighbor IP address."
    ::= { bwNSCongestionManagementNeighborEntry 1 }

bwNSCongestionManagementNeighborIpAddress OBJECT-TYPE
    SYNTAX      DisplayString
    MAX-ACCESS  read-only
    STATUS      current
    DESCRIPTION 
        "The IP address of the neighbor."
    ::= { bwNSCongestionManagementNeighborEntry 2 }

bwNSCongestionManagementNeighborInviteIn OBJECT-TYPE
    SYNTAX      Counter32
    MAX-ACCESS  read-write
    STATUS      current
    DESCRIPTION 
        "This is the number of Invite requests that the neighbor sends to the Network Server."
    ::= { bwNSCongestionManagementNeighborEntry 3 }

bwNSCongestionManagementNeighborRegisterIn OBJECT-TYPE
    SYNTAX      Counter32
    MAX-ACCESS  read-write
    STATUS      current
    DESCRIPTION 
        "This is the number of Register requests that the neighbor sends to the Network Server."
    ::= { bwNSCongestionManagementNeighborEntry 4 }

bwNSCongestionManagementNeighborOptionsIn OBJECT-TYPE
    SYNTAX      Counter32
    MAX-ACCESS  read-write
    STATUS      current
    DESCRIPTION 
        "This is the number of Options requests that the neighbor sends to the Network Server."
    ::= { bwNSCongestionManagementNeighborEntry 5 }

bwNSCongestionManagementNeighborOptionsOut OBJECT-TYPE
    SYNTAX      Counter32
    MAX-ACCESS  read-write
    STATUS      current
    DESCRIPTION 
        "This is the number of Options requests that the Network Server sends to the neighbor."
    ::= { bwNSCongestionManagementNeighborEntry 6 }

bwNSCongestionManagementNeighborSubscribeNotifyIn OBJECT-TYPE
    SYNTAX      Counter32
    MAX-ACCESS  read-write
    STATUS      current
    DESCRIPTION 
        "This is the number of Subscribe and Notify requests that the neighbor sends to the Network Server."
    ::= { bwNSCongestionManagementNeighborEntry 7 }

bwNSCongestionManagementNeighbor5xxIn OBJECT-TYPE
    SYNTAX      Counter32
    MAX-ACCESS  read-write
    STATUS      current
    DESCRIPTION 
        "This is the number of 5xx responses that the neighbor sends to the Network Server."
    ::= { bwNSCongestionManagementNeighborEntry 8 }

bwNSCongestionManagementNeighborCallpRequestInRate OBJECT-TYPE
    SYNTAX      Gauge32
    MAX-ACCESS  read-only
    STATUS      current
    DESCRIPTION 
        "This is the incoming callp requests rate."
    ::= { bwNSCongestionManagementNeighborEntry 9 }

bwNSCongestionManagementNeighborNonCallpRequestInRate OBJECT-TYPE
    SYNTAX      Gauge32
    MAX-ACCESS  read-only
    STATUS      current
    DESCRIPTION 
        "This is the incoming non-callp requests rate."
    ::= { bwNSCongestionManagementNeighborEntry 10 }

bwNSCongestionManagementNeighborState OBJECT-TYPE
    SYNTAX      DisplayString
    MAX-ACCESS  read-only
    STATUS      current
    DESCRIPTION 
        "The current congestion management state of the neighbor."
    ::= { bwNSCongestionManagementNeighborEntry 11 }

bwNSCongestionManagementNeighborCapability OBJECT-TYPE
    SYNTAX      DisplayString
    MAX-ACCESS  read-only
    STATUS      current
    DESCRIPTION 
        "The congestion management capability of the neighbor."
    ::= { bwNSCongestionManagementNeighborEntry 12 }

nrs OBJECT IDENTIFIER
    ::= { protocol 2 }

bwNSNbInvalidMessagesReceived OBJECT-TYPE
    SYNTAX      Counter32
    MAX-ACCESS  read-write
    STATUS      current
    DESCRIPTION 
        "This counter is incremented when an invalid NRS message is received (either the header was valid but the body was not, or the message was pure junk)"
    ::= { nrs 6 }

bwNSNbRequestsReceived OBJECT-TYPE
    SYNTAX      Counter32
    MAX-ACCESS  read-write
    STATUS      current
    DESCRIPTION 
        "This counter is incremented when a NRS request is received"
    ::= { nrs 7 }

bwNSNbResponsesReceived OBJECT-TYPE
    SYNTAX      Counter32
    MAX-ACCESS  read-write
    STATUS      current
    DESCRIPTION 
        "This counter is incremented when a NRS response is received"
    ::= { nrs 8 }

bwNSNbErrorsReceived OBJECT-TYPE
    SYNTAX      Counter32
    MAX-ACCESS  read-write
    STATUS      current
    DESCRIPTION 
        "This counter is incremented when a NRS error is received"
    ::= { nrs 9 }

bwNSNbRequestsSent OBJECT-TYPE
    SYNTAX      Counter32
    MAX-ACCESS  read-write
    STATUS      current
    DESCRIPTION 
        "This counter is incremented when a NRS request is sent"
    ::= { nrs 10 }

bwNSNbResponsesSent OBJECT-TYPE
    SYNTAX      Counter32
    MAX-ACCESS  read-write
    STATUS      current
    DESCRIPTION 
        "This counter is incremented when a NRS response is sent"
    ::= { nrs 11 }

bwNSNbErrorsSent OBJECT-TYPE
    SYNTAX      Counter32
    MAX-ACCESS  read-write
    STATUS      current
    DESCRIPTION 
        "This counter is incremented when a NRS error is sent"
    ::= { nrs 12 }

bwNSNbRequestsResent OBJECT-TYPE
    SYNTAX      Counter32
    MAX-ACCESS  read-write
    STATUS      current
    DESCRIPTION 
        "This counter is incremented when a NRS request is re-sent"
    ::= { nrs 13 }

bwNSNbResponsesResent OBJECT-TYPE
    SYNTAX      Counter32
    MAX-ACCESS  read-write
    STATUS      current
    DESCRIPTION 
        "This counter is incremented when a NRS response is re-sent"
    ::= { nrs 14 }

bwNSNbRequestsUnanswered OBJECT-TYPE
    SYNTAX      Counter32
    MAX-ACCESS  read-write
    STATUS      current
    DESCRIPTION 
        "This counter is incremented when a NRS request remains unanswered after a series of retries"
    ::= { nrs 15 }

bwNSNRSStatsTable OBJECT-TYPE
    SYNTAX      SEQUENCE OF BwNSNRSStatsEntry
    MAX-ACCESS  not-accessible
    STATUS      current
    DESCRIPTION 
        "This table contains the counters for all NRS protocols"
    ::= { nrs 16 }

bwNSNRSStatsEntry OBJECT-TYPE
    SYNTAX      BwNSNRSStatsEntry
    MAX-ACCESS  not-accessible
    STATUS      current
    DESCRIPTION 
        "This row contains information on a particular NRS protocol"
    INDEX       { bwNSNRSStatsTableIndex }
    ::= { bwNSNRSStatsTable 1 }

BwNSNRSStatsEntry ::= SEQUENCE {
    bwNSNRSStatsTableIndex                  Unsigned32,
    bwNSNRSStatsTableProtocolName           DisplayString,
    bwNSNRSStatsTableNbRequestsReceived     Counter32,
    bwNSNRSStatsTableNbResponsesReceived    Counter32,
    bwNSNRSStatsTableNbErrorsReceived       Counter32,
    bwNSNRSStatsTableNbRequestsSent         Counter32,
    bwNSNRSStatsTableNbResponsesSent        Counter32,
    bwNSNRSStatsTableNbErrorsSent           Counter32,
    bwNSNRSStatsTableNbRequestsResent       Counter32,
    bwNSNRSStatsTableNbResponsesResent      Counter32,
    bwNSNRSStatsTableNbRequestsUnanswered   Counter32
}

bwNSNRSStatsTableIndex OBJECT-TYPE
    SYNTAX      Unsigned32
    MAX-ACCESS  not-accessible
    STATUS      current
    DESCRIPTION 
        "This integer represents a NRS protocol status code.  The rest of the information in this row is related to this value."
    ::= { bwNSNRSStatsEntry 1 }

bwNSNRSStatsTableProtocolName OBJECT-TYPE
    SYNTAX      DisplayString
    MAX-ACCESS  read-only
    STATUS      current
    DESCRIPTION 
        "This string represents the NRS protocol name"
    ::= { bwNSNRSStatsEntry 2 }

bwNSNRSStatsTableNbRequestsReceived OBJECT-TYPE
    SYNTAX      Counter32
    MAX-ACCESS  read-write
    STATUS      current
    DESCRIPTION 
        "This counter is incremented when a request is received"
    ::= { bwNSNRSStatsEntry 3 }

bwNSNRSStatsTableNbResponsesReceived OBJECT-TYPE
    SYNTAX      Counter32
    MAX-ACCESS  read-write
    STATUS      current
    DESCRIPTION 
        "This counter is incremented when a response is received"
    ::= { bwNSNRSStatsEntry 4 }

bwNSNRSStatsTableNbErrorsReceived OBJECT-TYPE
    SYNTAX      Counter32
    MAX-ACCESS  read-write
    STATUS      current
    DESCRIPTION 
        "This counter is incremented when an error is received"
    ::= { bwNSNRSStatsEntry 5 }

bwNSNRSStatsTableNbRequestsSent OBJECT-TYPE
    SYNTAX      Counter32
    MAX-ACCESS  read-write
    STATUS      current
    DESCRIPTION 
        "This counter is incremented when a request is sent"
    ::= { bwNSNRSStatsEntry 6 }

bwNSNRSStatsTableNbResponsesSent OBJECT-TYPE
    SYNTAX      Counter32
    MAX-ACCESS  read-write
    STATUS      current
    DESCRIPTION 
        "This counter is incremented when a response is sent"
    ::= { bwNSNRSStatsEntry 7 }

bwNSNRSStatsTableNbErrorsSent OBJECT-TYPE
    SYNTAX      Counter32
    MAX-ACCESS  read-write
    STATUS      current
    DESCRIPTION 
        "This counter is incremented when an error is sent"
    ::= { bwNSNRSStatsEntry 8 }

bwNSNRSStatsTableNbRequestsResent OBJECT-TYPE
    SYNTAX      Counter32
    MAX-ACCESS  read-write
    STATUS      current
    DESCRIPTION 
        "This counter is incremented when a request is re-sent"
    ::= { bwNSNRSStatsEntry 9 }

bwNSNRSStatsTableNbResponsesResent OBJECT-TYPE
    SYNTAX      Counter32
    MAX-ACCESS  read-write
    STATUS      current
    DESCRIPTION 
        "This counter is incremented when a response is re-sent"
    ::= { bwNSNRSStatsEntry 10 }

bwNSNRSStatsTableNbRequestsUnanswered OBJECT-TYPE
    SYNTAX      Counter32
    MAX-ACCESS  read-write
    STATUS      current
    DESCRIPTION 
        "This counter is incremented when a request remains unanswered after a series of retries"
    ::= { bwNSNRSStatsEntry 11 }

callLog OBJECT IDENTIFIER
    ::= { protocol 6 }

calllogNbEnterprises OBJECT-TYPE
    SYNTAX      Gauge32
    MAX-ACCESS  read-only
    STATUS      current
    DESCRIPTION 
        "Number of enterprises for which call logging is enabled"
    ::= { callLog 1 }

calllogNbClients OBJECT-TYPE
    SYNTAX      Gauge32
    MAX-ACCESS  read-only
    STATUS      current
    DESCRIPTION 
        "Number of call log client that are currently connected to the NetworkServer"
    ::= { callLog 2 }

nsXSCommonCommStats OBJECT IDENTIFIER
    ::= { protocol 7 }

bwNSCommonCommXSStatsTable OBJECT-TYPE
    SYNTAX      SEQUENCE OF BwNSCommonCommXSStatsEntry
    MAX-ACCESS  not-accessible
    STATUS      current
    DESCRIPTION 
        "This table contains counters for BCCT for the XS process."
    ::= { nsXSCommonCommStats 1 }

bwNSCommonCommXSStatsEntry OBJECT-TYPE
    SYNTAX      BwNSCommonCommXSStatsEntry
    MAX-ACCESS  not-accessible
    STATUS      current
    DESCRIPTION 
        "Definition of the entries for bwNSCommonCommXSStatsTable."
    INDEX       { bwNSCommonCommXSStatsIndex }
    ::= { bwNSCommonCommXSStatsTable 1 }

BwNSCommonCommXSStatsEntry ::= SEQUENCE {
    bwNSCommonCommXSStatsIndex                      Unsigned32,
    bwNSCommonCommXSHost                            DisplayString,
    bwNSCommonCommXSInterface                       DisplayString,
    bwNSCommonCommXSProtocol                        DisplayString,
    bwNSCommonCommXSAcceptedOutboundConnections     Counter32,
    bwNSCommonCommXSAcceptedInboundConnections      Counter32,
    bwNSCommonCommXSRejectedOutboundConnections     Counter32,
    bwNSCommonCommXSRejectedInboundConnections      Counter32,
    bwNSCommonCommXSOutputMessagesProcessed         Counter32,
    bwNSCommonCommXSInputMessagesProcessed          Counter32,
    bwNSCommonCommXSOutputCommunicationErrors       Counter32,
    bwNSCommonCommXSInputCommunicationErrors        Counter32
}

bwNSCommonCommXSStatsIndex OBJECT-TYPE
    SYNTAX      Unsigned32
    MAX-ACCESS  read-only
    STATUS      current
    DESCRIPTION 
        "This integer represents an index in table bwNSCommonCommXSStatsTable. The index represents a connection for a specific Host-Interfacece-Protocol combination."
    ::= { bwNSCommonCommXSStatsEntry 1 }

bwNSCommonCommXSHost OBJECT-TYPE
    SYNTAX      DisplayString
    MAX-ACCESS  read-only
    STATUS      current
    DESCRIPTION 
        "The address of a host connected to the BroadWorks Common Communication Protocol."
    ::= { bwNSCommonCommXSStatsEntry 2 }

bwNSCommonCommXSInterface OBJECT-TYPE
    SYNTAX      DisplayString
    MAX-ACCESS  read-only
    STATUS      current
    DESCRIPTION 
        "The IP address of a local interface that a protocol is bound to."
    ::= { bwNSCommonCommXSStatsEntry 3 }

bwNSCommonCommXSProtocol OBJECT-TYPE
    SYNTAX      DisplayString
    MAX-ACCESS  read-only
    STATUS      current
    DESCRIPTION 
        "The name of a BroadWorks Common Communication Protocol client protocol, e.g. OCI or SyncApi."
    ::= { bwNSCommonCommXSStatsEntry 4 }

bwNSCommonCommXSAcceptedOutboundConnections OBJECT-TYPE
    SYNTAX      Counter32
    MAX-ACCESS  read-write
    STATUS      current
    DESCRIPTION 
        "This counter is incremented whenever a client in this process connects to the framework to a remote host, using the interface and protocol."
    ::= { bwNSCommonCommXSStatsEntry 5 }

bwNSCommonCommXSAcceptedInboundConnections OBJECT-TYPE
    SYNTAX      Counter32
    MAX-ACCESS  read-write
    STATUS      current
    DESCRIPTION 
        "This counter is incremented whenever a client in this process connects to the framework from a remote host, using the interface and protocol."
    ::= { bwNSCommonCommXSStatsEntry 6 }

bwNSCommonCommXSRejectedOutboundConnections OBJECT-TYPE
    SYNTAX      Counter32
    MAX-ACCESS  read-write
    STATUS      current
    DESCRIPTION 
        "This counter is incremented whenever a client connection request going from this process to a remote host and going through this interface has been rejected for a particular protocol."
    ::= { bwNSCommonCommXSStatsEntry 7 }

bwNSCommonCommXSRejectedInboundConnections OBJECT-TYPE
    SYNTAX      Counter32
    MAX-ACCESS  read-write
    STATUS      current
    DESCRIPTION 
        "This counter is incremented whenever a client connection request coming to this host and going through this interface has been rejected by the framework for a particular protocol."
    ::= { bwNSCommonCommXSStatsEntry 8 }

bwNSCommonCommXSOutputMessagesProcessed OBJECT-TYPE
    SYNTAX      Counter32
    MAX-ACCESS  read-write
    STATUS      current
    DESCRIPTION 
        "This counter is incremented whenever a message has been sent and processed for this host, interface and protocol."
    ::= { bwNSCommonCommXSStatsEntry 9 }

bwNSCommonCommXSInputMessagesProcessed OBJECT-TYPE
    SYNTAX      Counter32
    MAX-ACCESS  read-write
    STATUS      current
    DESCRIPTION 
        "This counter is incremented whenever a message has been received and processed for this host, interface and protocol."
    ::= { bwNSCommonCommXSStatsEntry 10 }

bwNSCommonCommXSOutputCommunicationErrors OBJECT-TYPE
    SYNTAX      Counter32
    MAX-ACCESS  read-write
    STATUS      current
    DESCRIPTION 
        "This counter is incremented whenever a message could not be read because the TCP stack returned an error."
    ::= { bwNSCommonCommXSStatsEntry 11 }

bwNSCommonCommXSInputCommunicationErrors OBJECT-TYPE
    SYNTAX      Counter32
    MAX-ACCESS  read-write
    STATUS      current
    DESCRIPTION 
        "This counter is incremented whenever a message has been sent and processed for this host, interface and protocol."
    ::= { bwNSCommonCommXSStatsEntry 12 }

tcp OBJECT IDENTIFIER
    ::= { protocol 8 }

bwNSXSTcpServersStatsTable OBJECT-TYPE
    SYNTAX      SEQUENCE OF BwNSXSTcpServersStatsEntry
    MAX-ACCESS  not-accessible
    STATUS      current
    DESCRIPTION 
        "This table contains counters for TCP underlying framework for the NSXS process."
    ::= { tcp 1 }

bwNSXSTcpServersStatsEntry OBJECT-TYPE
    SYNTAX      BwNSXSTcpServersStatsEntry
    MAX-ACCESS  not-accessible
    STATUS      current
    DESCRIPTION 
        "Definition of the entries for bwNSXSTcpServersStatsTable."
    INDEX       { bwNSXSTcpServersStatsIndex }
    ::= { bwNSXSTcpServersStatsTable 1 }

BwNSXSTcpServersStatsEntry ::= SEQUENCE {
    bwNSXSTcpServersStatsIndex              Unsigned32,
    bwNSXSTcpServersName                    DisplayString,
    bwNSXSTcpServersNbConnectionsAccepted   Counter32,
    bwNSXSTcpServersNbConnectionsRefused    Counter32,
    bwNSXSTcpServersNbConnectionsInitiated  Counter32,
    bwNSXSTcpServersNbConnectionsClosed     Counter32,
    bwNSXSTcpServersNbBytesSent             Gauge32,
    bwNSXSTcpServersNbBytesReceived         Gauge32,
    bwNSXSTcpServersOutgoingQueueSize       Gauge32,
    bwNSXSTcpServersIncomingQueueSize       Gauge32,
    bwNSXSTcpServersNbBytesSentSecure       Gauge32,
    bwNSXSTcpServersNbBytesReceivedSecure   Gauge32
}

bwNSXSTcpServersStatsIndex OBJECT-TYPE
    SYNTAX      Unsigned32
    MAX-ACCESS  read-only
    STATUS      current
    DESCRIPTION 
        "This integer represents an index in table bwNSXSTcpServersStatsTable. This is the index to a specific TCP server name."
    ::= { bwNSXSTcpServersStatsEntry 1 }

bwNSXSTcpServersName OBJECT-TYPE
    SYNTAX      DisplayString
    MAX-ACCESS  read-only
    STATUS      current
    DESCRIPTION 
        "The name of TCP server - Names are internally defined at at the application level."
    ::= { bwNSXSTcpServersStatsEntry 2 }

bwNSXSTcpServersNbConnectionsAccepted OBJECT-TYPE
    SYNTAX      Counter32
    MAX-ACCESS  read-write
    STATUS      current
    DESCRIPTION 
        "This counter represents the number of connections accepted by the TCP server."
    ::= { bwNSXSTcpServersStatsEntry 3 }

bwNSXSTcpServersNbConnectionsRefused OBJECT-TYPE
    SYNTAX      Counter32
    MAX-ACCESS  read-write
    STATUS      current
    DESCRIPTION 
        "This counter represents the number of connections refused by the TCP server."
    ::= { bwNSXSTcpServersStatsEntry 4 }

bwNSXSTcpServersNbConnectionsInitiated OBJECT-TYPE
    SYNTAX      Counter32
    MAX-ACCESS  read-write
    STATUS      current
    DESCRIPTION 
        "This counter represents the number of connections initiated by the TCP server."
    ::= { bwNSXSTcpServersStatsEntry 5 }

bwNSXSTcpServersNbConnectionsClosed OBJECT-TYPE
    SYNTAX      Counter32
    MAX-ACCESS  read-write
    STATUS      current
    DESCRIPTION 
        "This counter represents the number of connections closed by the TCP server or remote hosts."
    ::= { bwNSXSTcpServersStatsEntry 6 }

bwNSXSTcpServersNbBytesSent OBJECT-TYPE
    SYNTAX      Gauge32
    MAX-ACCESS  read-write
    STATUS      current
    DESCRIPTION 
        "This counter represents the number of bytes sent by the TCP server."
    ::= { bwNSXSTcpServersStatsEntry 7 }

bwNSXSTcpServersNbBytesReceived OBJECT-TYPE
    SYNTAX      Gauge32
    MAX-ACCESS  read-write
    STATUS      current
    DESCRIPTION 
        "This counter represents the number of bytes received by the TCP server."
    ::= { bwNSXSTcpServersStatsEntry 8 }

bwNSXSTcpServersOutgoingQueueSize OBJECT-TYPE
    SYNTAX      Gauge32
    MAX-ACCESS  read-only
    STATUS      current
    DESCRIPTION 
        "This counter represents the number of bytes in the outgoing queue."
    ::= { bwNSXSTcpServersStatsEntry 9 }

bwNSXSTcpServersIncomingQueueSize OBJECT-TYPE
    SYNTAX      Gauge32
    MAX-ACCESS  read-only
    STATUS      current
    DESCRIPTION 
        "This counter represents the number of bytes in the incoming queue."
    ::= { bwNSXSTcpServersStatsEntry 10 }

bwNSXSTcpServersNbBytesSentSecure OBJECT-TYPE
    SYNTAX      Gauge32
    MAX-ACCESS  read-write
    STATUS      current
    DESCRIPTION 
        "This counter represents the number of bytes sent by the TCP server over secure connections."
    ::= { bwNSXSTcpServersStatsEntry 11 }

bwNSXSTcpServersNbBytesReceivedSecure OBJECT-TYPE
    SYNTAX      Gauge32
    MAX-ACCESS  read-write
    STATUS      current
    DESCRIPTION 
        "This counter represents the number of bytes received by the TCP server over secure connections."
    ::= { bwNSXSTcpServersStatsEntry 12 }

persistency OBJECT IDENTIFIER
    ::= { nsExecutionServer 4 }

timesTen OBJECT IDENTIFIER
    ::= { persistency 1 }

ttNSNbConnectionsCreated OBJECT-TYPE
    SYNTAX      Counter32
    MAX-ACCESS  read-write
    STATUS      current
    DESCRIPTION 
        "This counter reflects the total number of connections that have been opened to the DB."
    ::= { timesTen 1 }

ttNSConnectionPoolSize OBJECT-TYPE
    SYNTAX      Gauge32
    MAX-ACCESS  read-only
    STATUS      current
    DESCRIPTION 
        "This gauge reflects the pool size of the DB."
    ::= { timesTen 2 }

xsRemoteXla OBJECT IDENTIFIER
    ::= { timesTen 5 }

xsNSRemoteXlaNbTimesConnected OBJECT-TYPE
    SYNTAX      Counter32
    MAX-ACCESS  read-write
    STATUS      current
    DESCRIPTION 
        "Number of times a connection was made to the RemoteXla server"
    ::= { xsRemoteXla 1 }

xsNSRemoteXlaNbTimesDisconnected OBJECT-TYPE
    SYNTAX      Counter32
    MAX-ACCESS  read-write
    STATUS      current
    DESCRIPTION 
        "Number of times the process was disconnected from the RemoteXla server"
    ::= { xsRemoteXla 2 }

xsNSRemoteXlaUpdatesProcessed OBJECT-TYPE
    SYNTAX      Counter32
    MAX-ACCESS  read-write
    STATUS      current
    DESCRIPTION 
        "Number of XLA updates processed"
    ::= { xsRemoteXla 3 }

xsNSRemoteXlaUpdatesPending OBJECT-TYPE
    SYNTAX      Gauge32
    MAX-ACCESS  read-write
    STATUS      current
    DESCRIPTION 
        "Number of XLA updates pending to be processed"
    ::= { xsRemoteXla 4 }

bwNSXSAvgUpdateTime OBJECT-TYPE
    SYNTAX      Gauge32
    MAX-ACCESS  read-only
    STATUS      current
    DESCRIPTION 
        "Average DB update time in milliseconds"
    ::= { timesTen 6 }

bwNSXSAvgRowsUpdated OBJECT-TYPE
    SYNTAX      Gauge32
    MAX-ACCESS  read-only
    STATUS      current
    DESCRIPTION 
        "Average number of rows affected in DB updates"
    ::= { timesTen 7 }

bwNSXSAvgQueryTime OBJECT-TYPE
    SYNTAX      Gauge32
    MAX-ACCESS  read-only
    STATUS      current
    DESCRIPTION 
        "Average DB query time in milliseconds"
    ::= { timesTen 8 }

bwNSXSAvgRowsQueried OBJECT-TYPE
    SYNTAX      Gauge32
    MAX-ACCESS  read-only
    STATUS      current
    DESCRIPTION 
        "Average number of rows processed in DB queries"
    ::= { timesTen 9 }

bwNSXSUpdateCount OBJECT-TYPE
    SYNTAX      Counter32
    MAX-ACCESS  read-write
    STATUS      current
    DESCRIPTION 
        "Number of DB updates performed since the application started"
    ::= { timesTen 10 }

bwNSXSQueryCount OBJECT-TYPE
    SYNTAX      Counter32
    MAX-ACCESS  read-write
    STATUS      current
    DESCRIPTION 
        "Number of DB queries performed since the application started"
    ::= { timesTen 11 }

bwNSXSTTHWMTable OBJECT-TYPE
    SYNTAX      SEQUENCE OF BwNSXSTTHWMEntry
    MAX-ACCESS  not-accessible
    STATUS      current
    DESCRIPTION 
        "This table contains counters for the XS TimesTen high water marks."
    ::= { timesTen 12 }

bwNSXSTTHWMEntry OBJECT-TYPE
    SYNTAX      BwNSXSTTHWMEntry
    MAX-ACCESS  not-accessible
    STATUS      current
    DESCRIPTION 
        "Definition of the entries for bwNSXSTTHWMTable."
    INDEX       { bwNSXSTTHWMIndex }
    ::= { bwNSXSTTHWMTable 1 }

BwNSXSTTHWMEntry ::= SEQUENCE {
    bwNSXSTTHWMIndex        Unsigned32,
    bwNSXSTTHWMName         DisplayString,
    bwNSXSTTHWMValue        Gauge32,
    bwNSXSTTHWMTimestamp    DisplayString,
    bwNSXSTTHWMStackTrace   DisplayString
}

bwNSXSTTHWMIndex OBJECT-TYPE
    SYNTAX      Unsigned32
    MAX-ACCESS  read-only
    STATUS      current
    DESCRIPTION 
        "This integer represents an index in table bwNSXSTTHWMTable. This is the index to a specific high water mark."
    ::= { bwNSXSTTHWMEntry 1 }

bwNSXSTTHWMName OBJECT-TYPE
    SYNTAX      DisplayString
    MAX-ACCESS  read-only
    STATUS      current
    DESCRIPTION 
        "The name of an XS TimesTen high water mark."
    ::= { bwNSXSTTHWMEntry 2 }

bwNSXSTTHWMValue OBJECT-TYPE
    SYNTAX      Gauge32
    MAX-ACCESS  read-write
    STATUS      current
    DESCRIPTION 
        "The value of an XS TimesTen high water mark."
    ::= { bwNSXSTTHWMEntry 3 }

bwNSXSTTHWMTimestamp OBJECT-TYPE
    SYNTAX      DisplayString
    MAX-ACCESS  read-write
    STATUS      current
    DESCRIPTION 
        "The timestamp of an XS TimesTen high water mark."
    ::= { bwNSXSTTHWMEntry 4 }

bwNSXSTTHWMStackTrace OBJECT-TYPE
    SYNTAX      DisplayString
    MAX-ACCESS  read-write
    STATUS      current
    DESCRIPTION 
        "The stack trace of an XS TimesTen high water mark."
    ::= { bwNSXSTTHWMEntry 5 }

perNSNbOpenedTransactions OBJECT-TYPE
    SYNTAX      Counter32
    MAX-ACCESS  read-write
    STATUS      current
    DESCRIPTION 
        "This gauge reflects the total number of transactions currently opened."
    ::= { persistency 2 }

perNSNbCommittedTransactions OBJECT-TYPE
    SYNTAX      Counter32
    MAX-ACCESS  read-write
    STATUS      current
    DESCRIPTION 
        "This counter reflects the total number of committed transactions."
    ::= { persistency 3 }

perNSNbFailedTransactions OBJECT-TYPE
    SYNTAX      Counter32
    MAX-ACCESS  read-write
    STATUS      current
    DESCRIPTION 
        "This counter reflects the total number of failed transactions."
    ::= { persistency 4 }

perNSNbCriticalErrors OBJECT-TYPE
    SYNTAX      Counter32
    MAX-ACCESS  read-write
    STATUS      current
    DESCRIPTION 
        "This counter reflects the total number of critical errors that occurred in the persistency layer of the network server."
    ::= { persistency 5 }

management OBJECT IDENTIFIER
    ::= { nsExecutionServer 5 }

resetAllNSXSCounters OBJECT-TYPE
    SYNTAX      Counter32
    MAX-ACCESS  read-write
    STATUS      current
    DESCRIPTION 
        "When set to a value other then 0, all the counters in the system are reset to 0."
    ::= { management 1 }

serviceControlProxy OBJECT IDENTIFIER
    ::= { nsExecutionServer 6 }

concurrent OBJECT IDENTIFIER
    ::= { nsExecutionServer 7 }

bwNSXSMonitoringExecutorTable OBJECT-TYPE
    SYNTAX      SEQUENCE OF BwNSXSMonitoringExecutorEntry
    MAX-ACCESS  not-accessible
    STATUS      current
    DESCRIPTION 
        "This table contains counters for the concurrent framework."
    ::= { concurrent 1 }

bwNSXSMonitoringExecutorEntry OBJECT-TYPE
    SYNTAX      BwNSXSMonitoringExecutorEntry
    MAX-ACCESS  not-accessible
    STATUS      current
    DESCRIPTION 
        "Definition of the entries for bwNSXSMonitoringExecutorTable."
    INDEX       { bwNSXSMonitoringExecutorIndex }
    ::= { bwNSXSMonitoringExecutorTable 1 }

BwNSXSMonitoringExecutorEntry ::= SEQUENCE {
    bwNSXSMonitoringExecutorIndex               Unsigned32,
    bwNSXSMonitoringExecutorName                DisplayString,
    bwNSXSMonitoringExecutorCurrentPoolSize     Gauge32,
    bwNSXSMonitoringExecutorMaxPoolSize         Gauge32,
    bwNSXSMonitoringExecutorAvgActiveThreads    Gauge32,
    bwNSXSMonitoringExecutorTaskQueueSize       Gauge32,
    bwNSXSMonitoringExecutorNbTasksRun          Counter32,
    bwNSXSMonitoringExecutorNbWarnings          Counter32,
    bwNSXSMonitoringExecutorNbErrors            Counter32,
    bwNSXSMonitoringExecutorLongestTaskMs       Gauge32,
    bwNSXSMonitoringExecutorLongestTaskName     DisplayString
}

bwNSXSMonitoringExecutorIndex OBJECT-TYPE
    SYNTAX      Unsigned32
    MAX-ACCESS  read-only
    STATUS      current
    DESCRIPTION 
        "This integer represents an index in table bwNSXSMonitoringExecutorTable. This is the index to a specific Monitoring Executor name."
    ::= { bwNSXSMonitoringExecutorEntry 1 }

bwNSXSMonitoringExecutorName OBJECT-TYPE
    SYNTAX      DisplayString
    MAX-ACCESS  read-only
    STATUS      current
    DESCRIPTION 
        "The name of the Monitoring Executor - Names are internally defined at the application level."
    ::= { bwNSXSMonitoringExecutorEntry 2 }

bwNSXSMonitoringExecutorCurrentPoolSize OBJECT-TYPE
    SYNTAX      Gauge32
    MAX-ACCESS  read-only
    STATUS      current
    DESCRIPTION 
        "The current thread pool size"
    ::= { bwNSXSMonitoringExecutorEntry 3 }

bwNSXSMonitoringExecutorMaxPoolSize OBJECT-TYPE
    SYNTAX      Gauge32
    MAX-ACCESS  read-only
    STATUS      current
    DESCRIPTION 
        "The maximum thread pool size"
    ::= { bwNSXSMonitoringExecutorEntry 4 }

bwNSXSMonitoringExecutorAvgActiveThreads OBJECT-TYPE
    SYNTAX      Gauge32
    MAX-ACCESS  read-only
    STATUS      current
    DESCRIPTION 
        "The average number of active threads, rounded up"
    ::= { bwNSXSMonitoringExecutorEntry 5 }

bwNSXSMonitoringExecutorTaskQueueSize OBJECT-TYPE
    SYNTAX      Gauge32
    MAX-ACCESS  read-only
    STATUS      current
    DESCRIPTION 
        "Number of tasks in the queue (includes scheduled and recurring tasks)"
    ::= { bwNSXSMonitoringExecutorEntry 6 }

bwNSXSMonitoringExecutorNbTasksRun OBJECT-TYPE
    SYNTAX      Counter32
    MAX-ACCESS  read-write
    STATUS      current
    DESCRIPTION 
        "Number of tasks run"
    ::= { bwNSXSMonitoringExecutorEntry 7 }

bwNSXSMonitoringExecutorNbWarnings OBJECT-TYPE
    SYNTAX      Counter32
    MAX-ACCESS  read-write
    STATUS      current
    DESCRIPTION 
        "Number of warnings that occured"
    ::= { bwNSXSMonitoringExecutorEntry 8 }

bwNSXSMonitoringExecutorNbErrors OBJECT-TYPE
    SYNTAX      Counter32
    MAX-ACCESS  read-write
    STATUS      current
    DESCRIPTION 
        "Number of errors that occured"
    ::= { bwNSXSMonitoringExecutorEntry 9 }

bwNSXSMonitoringExecutorLongestTaskMs OBJECT-TYPE
    SYNTAX      Gauge32
    MAX-ACCESS  read-only
    STATUS      current
    DESCRIPTION 
        "Longest completed task execution time in milliseconds"
    ::= { bwNSXSMonitoringExecutorEntry 10 }

bwNSXSMonitoringExecutorLongestTaskName OBJECT-TYPE
    SYNTAX      DisplayString
    MAX-ACCESS  read-only
    STATUS      current
    DESCRIPTION 
        "Longest completed task name"
    ::= { bwNSXSMonitoringExecutorEntry 11 }

bwNSMibConformance OBJECT IDENTIFIER
    ::= { nsExecutionServer 100 }

bwNSMibGroups OBJECT IDENTIFIER
    ::= { bwNSMibConformance 1 }

bwNSMibCompliancy OBJECT IDENTIFIER
    ::= { bwNSMibConformance 2 }

bwNSLicensingGroup OBJECT-GROUP
    OBJECTS     { bwNbTimePeriodWithLicenseViolations, 
                  bwNbTransactionInViolation, bwNbThresholdAlarmSent, 
                  bwNSSystemInternalQueueResets,
                  bwNbNonInviteTimePeriodWithLicenseViolations,
                  bwNbNonInviteTransactionInViolation,
                  bwNbNonInviteThresholdAlarmSent }
    STATUS      current
    DESCRIPTION 
        "This group defines the licensing information for the Network Server."
    ::= { bwNSMibGroups 1 }

bwNSSystemQueueStatsGroup OBJECT-GROUP
    OBJECTS     { bwNSSystemInternalQueueResets, 
                  bwNSSystemInternalQueueIndex, 
                  bwNSSystemInternalQueueName, 
                  bwNSSystemInternalQueueSize, 
                  bwNSSystemInternalQueueTimeAvg, 
                  bwNSSystemInternalQueueTimeMin, 
                  bwNSSystemInternalQueueTimeMax, 
                  bwNSSystemInternalQueueTimeMaxTimestampMSB, 
                  bwNSSystemInternalQueueLengthCurrent, 
                  bwNSSystemInternalQueueLengthAvg, 
                  bwNSSystemInternalQueueLengthMax, 
                  bwNSSystemInternalQueueLengthMaxTimestampMSB, 
                  bwNSSystemInternalQueueLengthMaxTimestampLSB, 
                  bwNSSystemInternalQueueTimeMaxTimestampLSB }
    STATUS      current
    DESCRIPTION 
        "This group defines the internal system queue statistics information the Network Server."
    ::= { bwNSMibGroups 2 }

bwNSGenericPolicyStatsGroup OBJECT-GROUP
    OBJECTS     { pubPolStatPolicyName, pubPolStatNbInstances, 
                  pubPolStatNbRequests, pubPolStatNbRequestsFailures, 
                  pubPolStatNbRequestsResults, privPolStatEnterpriseName, 
                  privPolStatPolicyName, privPolStatNbRequests, 
                  privPolStatNbRequestsFailures, 
                  privPolStatNbRequestsResults, polInfoEnterpriseName, 
                  polInfoPolicyName, polInfoInfoName, 
                  polInfoNbOccurences, bwNbPolicyRequests, 
                  bwNbPolicyRequestFailures }
    STATUS      current
    DESCRIPTION 
        "This group defines the generic counter for all policies on the Network Server."
    ::= { bwNSMibGroups 3 }

bwNSNeStatsGroup OBJECT-GROUP
    OBJECTS     { neStatName, neStatNbSIPRequests, 
                  neStatNbSIPRequestsFailures, neStatNbMSSRequests, 
                  neStatNbMSSRequestsFailures }
    STATUS      current
    DESCRIPTION 
        "This group defines the information for the Network Elements sending requests to the Network Server."
    ::= { bwNSMibGroups 4 }

bwNSErrorStatsGroup OBJECT-GROUP
    OBJECTS     { errStatName, errStatNbOccurences }
    STATUS      current
    DESCRIPTION 
        "This group defines statistics for all error codes returned by the Network Server to SIP requests."
    ::= { bwNSMibGroups 5 }

bwNSCallPStatsGroup OBJECT-GROUP
    OBJECTS     { bwNSCallpCallsPerSecond, bwNSCallpNumberOfActiveSessions }
    STATUS      current
    DESCRIPTION 
        "This group defines statistics for system level callp of the Network Server."
    ::= { bwNSMibGroups 6 }

bwNSCarrierStatsGroup OBJECT-GROUP
    OBJECTS     { bwCarrierName, bwCarrierCic, bwCarrierNbIntraLataCalls, 
                  bwCarrierNbInterLataCalls, 
                  bwCarrierNbInternationalCalls }
    STATUS      current
    DESCRIPTION 
        "This group defines statistics per equal acess carrier."
    ::= { bwNSMibGroups 7 }

bwNSSipStatsGroup OBJECT-GROUP
    OBJECTS     { bwNSSipStatsInviteIns, bwNSSipStatsAckIns, 
                  bwNSSipStatsCancelIns, bwNSSipStatsRegisterIns, 
                  bwNSSipStatsNotifyIns, bwNSSipStatsSubscribeIns, 
                  bwNSSipStatsMessageIns, bwNSSipStatsInfoIns, 
                  bwNSSipStatsOptionsIns, bwNSSipStatsFailures, 
                  bwNSSipStatsActiveTcpConnections, bwNSSipStatsTcpIns, 
                  bwNSSipStatsTcpOuts, bwNSSipStatsTcpFailures, 
                  bwNSSipStatsUdpIns, bwNSSipStatsUdpOuts,
                  bwNSSIPReclaimedStaleTcpConnections, 
                  bwNSSipStatsInviteResponseOuts, 
                  bwNSSipStatsOptionsResponseIns, 
                  bwNSSipStatsOptionsResponseOuts, 
                  bwNSSipStatsRegisterResponseIns, 
                  bwNSSipStatsRegisterResponseOuts, 
                  bwNSSipStatsInfoResponseIns, 
                  bwNSSipStatsInfoResponseOuts, 
                  bwNSSipStatsNotifyResponseIns, 
                  bwNSSipStatsNotifyResponseOuts, 
                  bwNSSipStatsSubscribeResponseIns, 
                  bwNSSipStatsSubscribeResponseOuts, 
                  bwNSSipStatsMessageResponseIns, 
                  bwNSSipStatsMessageResponseOuts }
    STATUS      current
    DESCRIPTION 
        "This group defines statistics for the SIP protocol."
    ::= { bwNSMibGroups 8 }

bwNSNrsStatsGroup OBJECT-GROUP
    OBJECTS     { bwNSNbInvalidMessagesReceived, bwNSNbRequestsReceived, 
                  bwNSNbResponsesReceived, bwNSNbErrorsReceived, 
                  bwNSNbRequestsSent, bwNSNbResponsesSent, 
                  bwNSNbErrorsSent, bwNSNbRequestsResent, 
                  bwNSNbResponsesResent, bwNSNbRequestsUnanswered, 
                  bwNSNRSStatsTableProtocolName, 
                  bwNSNRSStatsTableNbRequestsReceived, 
                  bwNSNRSStatsTableNbResponsesReceived, 
                  bwNSNRSStatsTableNbErrorsReceived, 
                  bwNSNRSStatsTableNbRequestsSent, 
                  bwNSNRSStatsTableNbResponsesSent, 
                  bwNSNRSStatsTableNbErrorsSent, 
                  bwNSNRSStatsTableNbRequestsResent, 
                  bwNSNRSStatsTableNbResponsesResent, 
                  bwNSNRSStatsTableNbRequestsUnanswered }
    STATUS      current
    DESCRIPTION 
        "This group defines statistics for the NRS-based protocols."
    ::= { bwNSMibGroups 9 }

bwNSCallLogsStatsGroup OBJECT-GROUP
    OBJECTS     { calllogNbEnterprises, calllogNbClients }
    STATUS      current
    DESCRIPTION 
        "This group defines statistics for the call logs."
    ::= { bwNSMibGroups 10 }

bwNSXSPersistencyStatsGroup OBJECT-GROUP
    OBJECTS     { perNSNbOpenedTransactions, 
                  perNSNbCommittedTransactions, 
                  perNSNbFailedTransactions, perNSNbCriticalErrors, 
                  ttNSNbConnectionsCreated, ttNSConnectionPoolSize, 
                  bwNSXSAvgUpdateTime, bwNSXSAvgRowsUpdated,
                  bwNSXSAvgQueryTime, bwNSXSAvgRowsQueried,
                  bwNSXSUpdateCount, bwNSXSQueryCount,
                  bwNSXSTTHWMIndex, bwNSXSTTHWMName,
                  bwNSXSTTHWMValue, bwNSXSTTHWMTimestamp,
                  bwNSXSTTHWMStackTrace,
                  xsNSRemoteXlaNbTimesConnected, 
                  xsNSRemoteXlaNbTimesDisconnected, 
                  xsNSRemoteXlaUpdatesProcessed, 
                  xsNSRemoteXlaUpdatesPending }
    STATUS      current
    DESCRIPTION 
        "This group defines statistics for the Network Server Execution Server process persistency."
    ::= { bwNSMibGroups 11 }

bwNSMoCountersGroup OBJECT-GROUP
    OBJECTS     { resetAllNSXSCounters }
    STATUS      current
    DESCRIPTION 
        "This group defines statistics to perform managed object work for the Network Server."
    ::= { bwNSMibGroups 12 }

bwNSXSBcctGroup OBJECT-GROUP
    OBJECTS     { bwNSCommonCommXSStatsIndex, bwNSCommonCommXSHost, 
                  bwNSCommonCommXSInterface, bwNSCommonCommXSProtocol, 
                  bwNSCommonCommXSAcceptedOutboundConnections, 
                  bwNSCommonCommXSAcceptedInboundConnections, 
                  bwNSCommonCommXSRejectedOutboundConnections, 
                  bwNSCommonCommXSRejectedInboundConnections, 
                  bwNSCommonCommXSOutputMessagesProcessed, 
                  bwNSCommonCommXSInputMessagesProcessed, 
                  bwNSCommonCommXSOutputCommunicationErrors, 
                  bwNSCommonCommXSInputCommunicationErrors }
    STATUS      current
    DESCRIPTION 
        "This group defines the statistics for the BCCT protocol for the Network Server Execution Server process."
    ::= { bwNSMibGroups 19 }

bwNSXSTcpStatsGroup OBJECT-GROUP
    OBJECTS     { bwNSXSTcpServersStatsIndex, bwNSXSTcpServersName, 
                  bwNSXSTcpServersNbConnectionsAccepted, 
                  bwNSXSTcpServersNbConnectionsRefused,
                  bwNSXSTcpServersNbConnectionsInitiated,
                  bwNSXSTcpServersNbConnectionsClosed, 
                  bwNSXSTcpServersOutgoingQueueSize, 
                  bwNSXSTcpServersIncomingQueueSize, 
                  bwNSXSTcpServersNbBytesSent,
                  bwNSXSTcpServersNbBytesSentSecure, 
                  bwNSXSTcpServersNbBytesReceived,
                  bwNSXSTcpServersNbBytesReceivedSecure }
    STATUS      current
    DESCRIPTION 
        "This group defines the statistics for the Automatic Hold And Retrieve Service."
    ::= { bwNSMibGroups 21 }

bwNSXSConcurrentFrameworkStatsGroup OBJECT-GROUP
    OBJECTS     { bwNSXSMonitoringExecutorIndex, 
                  bwNSXSMonitoringExecutorName, 
                  bwNSXSMonitoringExecutorCurrentPoolSize, 
                  bwNSXSMonitoringExecutorMaxPoolSize, 
                  bwNSXSMonitoringExecutorAvgActiveThreads, 
                  bwNSXSMonitoringExecutorTaskQueueSize, 
                  bwNSXSMonitoringExecutorNbTasksRun, 
                  bwNSXSMonitoringExecutorNbWarnings, 
                  bwNSXSMonitoringExecutorNbErrors, 
                  bwNSXSMonitoringExecutorLongestTaskMs, 
                  bwNSXSMonitoringExecutorLongestTaskName }
    STATUS      current
    DESCRIPTION 
        "This group defines the statistics for the Automatic Hold And Retrieve Service."
    ::= { bwNSMibGroups 23 }

bwNSXSCongestionManagementGroup OBJECT-GROUP
    OBJECTS     { bwNSCurrentCallOverloadZone, 
                  bwNSNumCallYellowZoneOverloadTrans, 
                  bwNSNumCallRedZoneOverloadTrans, 
                  bwNSCurrentNonCallOverloadZone, 
                  bwNSNumNonCallYellowZoneOverloadTrans, 
                  bwNSNumNonCallRedZoneOverloadTrans, 
                  bwNSNumDiscardedMessage, bwNSTimeLastDiscardedMessage,
                  bwNSMemoryHighWaterMark, bwNSMemoryHighWaterMarkTimeMSB,
                  bwNSMemoryHighWaterMarkTimeLSB, bwNSOverloadStatsReset,
                  bwNSOverloadSampledDataIndex, bwNSOverloadSampledDataName,
                  bwNSOverloadSampledDelayMin, bwNSOverloadSampledDelayAvg,
                  bwNSOverloadSampledDelayMax, bwNSOverloadSampledDelayMaxTimeMSB,
                  bwNSOverloadSampledDelayMaxTimeLSB, bwNSOverloadNumSamples }
    STATUS      current
    DESCRIPTION 
        "This group defines the statistics for the Congestion Management."
    ::= { bwNSMibGroups 25 }

bwSIPCongestionManagementGroup OBJECT-GROUP
    OBJECTS     { bwNSCongestionManagementNeighborIpAddress, 
                  bwNSCongestionManagementNeighborInviteIn, 
                  bwNSCongestionManagementNeighborRegisterIn, 
                  bwNSCongestionManagementNeighborOptionsIn, 
                  bwNSCongestionManagementNeighborOptionsOut, 
                  bwNSCongestionManagementNeighborSubscribeNotifyIn, 
                  bwNSCongestionManagementNeighbor5xxIn, 
                  bwNSCongestionManagementNeighborCallpRequestInRate, 
                  bwNSCongestionManagementNeighborNonCallpRequestInRate, 
                  bwNSCongestionManagementNeighborState, 
                  bwNSCongestionManagementNeighborCapability }
    STATUS      current
    DESCRIPTION 
        "This group defines the statistics for the SIP Congestion Management."
    ::= { bwNSMibGroups 26 }

bwNSBasicCompliance MODULE-COMPLIANCE
    STATUS      current
    DESCRIPTION 
        "BroadWorks Network Server MIB compliance"

    MODULE      -- this module

        MANDATORY-GROUPS        { bwNSLicensingGroup, 
                  bwNSSystemQueueStatsGroup, bwNSGenericPolicyStatsGroup, 
                  bwNSNeStatsGroup, bwNSErrorStatsGroup, 
                  bwNSCallPStatsGroup, bwNSCarrierStatsGroup, 
                  bwNSSipStatsGroup, bwNSNrsStatsGroup, 
                  bwNSCallLogsStatsGroup, bwNSXSPersistencyStatsGroup, 
                  bwNSMoCountersGroup, bwNSXSTcpStatsGroup, 
                  bwNSXSCongestionManagementGroup, 
                  bwSIPCongestionManagementGroup }

    ::= { bwNSMibCompliancy 1 }

END -- end of module BW-NSExecution.
